module itut-eth-oam-deviation-example {
  yang-version 1.1;
  namespace
    "https://itut.example.com/yang/itut-eth-oam-deviation-example";
  prefix eth-oam-dev;

  import ieee802-dot1q-cfm {
    prefix dot1q-cfm;
    reference
      "IEEE Std 802.1Qcx-2020";
  }
  import itut-eth-oam {
    prefix eth-oam;
    reference
      "G.8052.1 v2.0 (06/2025)";
  }

  organization
    "ITU-T Study Group 15 (SG15) - International Telecommunication
     Union";
  contact
    "tsbsg15@itu.int";
  description
    "This module defines an example of a YANG data model containing
     the YANG deviation statements to declare that an implementation
     compliant with ITU-T G.8021 does not support YANG data nodes
     which are mandatory for implementations compliant with IEEE
     802.1Q CFM but not required by implementations compliant with
     ITU-T G.8021.

     Copyright(C) ITU (2025).

     All rights reserved. This version of this YANG module is part of
     ITU-T G.8052.1 Operation, administration, maintenance (OAM)
     management information and data models for the
     Ethernet-transport network element; see the Recommendation
     itself for full legal notices.";

  revision 2025-06-13 {
    description
      "Initial version.";
    reference
      "G.8052.1 v2.0 (06/2025)";
  }

  /*
   * Deviations
   */

  deviation "/dot1q-cfm:cfm/dot1q-cfm:maintenance-group"
          + "/dot1q-cfm:mep/dot1q-cfm:inactive-remote-mep" {
    description
      "Implementations compliant with ITU-T G.8021 are not required
       to support inactive MEPs.";
    reference
      "IEEE Std 802.1Q-2018: clause 12.14.7.1.3ae

       ITU-T G.8021 v8.1 (01/2024): clause 8";
    deviate not-supported;
  }

  deviation "/dot1q-cfm:cfm/dot1q-cfm:maintenance-group"
          + "/dot1q-cfm:mep/dot1q-cfm:mep-db"
          + "/dot1q-cfm:rmep-failed-ok-time" {
    description
      "Implementations compliant with ITU-T G.8021 are not required
       to report time (SysUpTime) at which the Remote MEP state
       machine last entered either the RMEP_FAILED or RMEP_OK
       state.";
    reference
      "ITU-T G.8021 v8.1 (01/2024): clause 8.1.7

       IEEE Std 802.1Q-2018: clause 12.14.7.6.3c";
    deviate not-supported;
  }

  deviation "/dot1q-cfm:cfm/dot1q-cfm:maintenance-group"
          + "/dot1q-cfm:mep/dot1q-cfm:mep-db/dot1q-cfm:mac-address" {
    description
      "Implementations compliant with ITU-T G.8021 are not required
       to report the MAC address of the remote MEP.";
    reference
      "ITU-T G.8021 v8.1 (01/2024): clause 8.1.7

       IEEE Std 802.1Q-2018: clauses 12.14.7.6.3d and 20.19.7";
    deviate not-supported;
  }

  deviation "/dot1q-cfm:cfm/dot1q-cfm:maintenance-group"
          + "/dot1q-cfm:mep/dot1q-cfm:mep-db"
          + "/dot1q-cfm:port-status-tlv" {
    description
      "Implementations compliant with ITU-T G.8021 are not required
       to process the Port status TLV in the received CCM OAM
       messages.";
    reference
      "ITU-T G.8021 v8.1 (01/2024): clause 8.1.7

       IEEE Std 802.1Q-2018: clauses 12.14.7.6.3f and 20.19.3";
    deviate not-supported;
  }

  deviation "/dot1q-cfm:cfm/dot1q-cfm:maintenance-group"
          + "/dot1q-cfm:mep/dot1q-cfm:mep-db"
          + "/dot1q-cfm:interface-status-tlv" {
    description
      "Implementations compliant with ITU-T G.8021 are not required
       to process the Interface status TLV in the received CCM OAM
       messages.";
    reference
      "ITU-T G.8021 v8.1 (01/2024): clause 8.1.7

       IEEE Std 802.1Q-2018: clauses 12.14.7.6.3g and 20.19.4";
    deviate not-supported;
  }

  deviation "/dot1q-cfm:cfm/dot1q-cfm:maintenance-group"
          + "/dot1q-cfm:mep/dot1q-cfm:linktrace-reply" {
    description
      "Equipment compliant with G.8021 are only required to report
       the results of the latest OAM Linktrace operation
       (itut-eth-oam:linktrace-state).";
    reference
      "ITU-T G.8021 v8.1 (01/2024): clause 8.1.13";
    deviate not-supported;
  }

  deviation "/dot1q-cfm:cfm/dot1q-cfm:maintenance-group/"
          + "dot1q-cfm:mep/dot1q-cfm:transmit-loopback"
          + "/dot1q-cfm:input/eth-oam:loopback-operation" {
    description
      "Implementations compliant with ITU-T G.8021 are required to
       support only ITU-T Loopback operations.

       In this case, the configuration of the type of ITU-T OAM
       Loopback (Discovery or Series) operation being requested is
       mandatory.";
    reference
      "ITU-T G.8021 v8.1 (01/2024): clause 8.1.8";
    deviate add {
      mandatory true;
    }
  }

  deviation "/dot1q-cfm:cfm/dot1q-cfm:maintenance-group"
          + "/dot1q-cfm:mep/dot1q-cfm:transmit-loopback"
          + "/dot1q-cfm:input/dot1q-cfm:lbm-destination" {
    description
      "Implementations compliant with ITU-T G.8021 are not required
       to configure the destination of the transmitted LBM OAM
       messages for OAM Loopback Discovery operations.";
    reference
      "ITU-T G.8021 v8.1 (01/2024): clause 8.1.8";
    deviate replace {
      mandatory false;
    }
  }

  deviation "/dot1q-cfm:cfm/dot1q-cfm:maintenance-group"
          + "/dot1q-cfm:mep/dot1q-cfm:transmit-loopback"
          + "/dot1q-cfm:input/dot1q-cfm:lbm-destination"
          + "/dot1q-cfm:dest-mcast-class1-mac-address"
          + "/dot1q-cfm:lbm-dest-mcast-class1-mac-address" {
    description
      "Implementations compliant only with ITU-T G.8021 are not to
       support the configuration of the multicast class 1 MAC
       address:
       - it is set by the system to the multicast class 1 MAC address
         corresponding to the Maintenance Domain (MD) level
         (MEG level) of the MEP when an ITU-T Loopback Discovery
         operation is requested;
       - it cannot be configured when an ITU-T Loopback Series
         operation is requested.";
    reference
      "ITU-T G.8021 v8.1 (01/2024): clause 8.1.8";
    deviate not-supported;
  }

  deviation "/dot1q-cfm:cfm/dot1q-cfm:maintenance-group"
          + "/dot1q-cfm:mep/dot1q-cfm:transmit-loopback"
          + "/dot1q-cfm:input"
          + "/dot1q-cfm:lbm-destination/dot1q-cfm:dest-mep-id"
          + "/dot1q-cfm:lbm-dest-mep-id" {
    description
      "Implementations compliant with ITU-T G.8021 are only required
       to support the configuration of the Target MAC address
       (lbm-dest-ucast-mac-address) for OAM Loopback Series
       operations.";
    reference
      "ITU-T G.8021 v8.1 (01/2024): clause 8.1.8";
    deviate not-supported;
  }

  deviation "/dot1q-cfm:cfm/dot1q-cfm:maintenance-group"
          + "/dot1q-cfm:mep/dot1q-cfm:transmit-loopback"
          + "/dot1q-cfm:input/eth-oam:loopback-operation"
          + "/eth-oam:loopback-discovery"
          + "/eth-oam:loopback-discovery" {
    description
      "Implementations compliant with ITU-T G.8021 are not required
       to configure any attributes for OAM Loopback Discovery
       operations.";
    reference
      "ITU-T G.8021 v8.1 (01/2024): clause 8.1.8";
    deviate delete {
      must 'not (../dot1q-cfm:lbm-data-tlv)';
    }
    deviate add {
      must 'not (../dot1q-cfm:lbm-dest-ucast-mac-address)' {
        description
          "When an ITU-T OAM Loopback Discovery operation is
           requested, the Target MAC Address shall not be configured:
           the system shall configure, by default, the multicast
           class 1 MAC address corresponding to the Maintenance
           Domain (MD) level (MEG level) of the MEP.";
      }
      must 'not (../dot1q-cfm:lbm-priority)' {
        description
          "When an ITU-T OAM Loopback Discovery operation is
           requested, the LBM Priority shall not be configured: the
           system shall configure, by default, the same value as the
           CCM priority.";
      }
    }
  }

  deviation "/dot1q-cfm:cfm/dot1q-cfm:maintenance-group"
          + "/dot1q-cfm:mep/dot1q-cfm:transmit-loopback"
          + "/dot1q-cfm:input/dot1q-cfm:lbm-priority" {
    description
      "The default value is the same as the CCM priority in
       implementations compliant with ITU-T G.8021 for OAM Loopback
       Series operations.";
    reference
      "ITU-T G.8021 v8.1 (01/2024): clause 8.1.8";
    deviate delete {
      default "7";
    }
  }

  deviation "/dot1q-cfm:cfm/dot1q-cfm:maintenance-group"
          + "/dot1q-cfm:mep/dot1q-cfm:transmit-loopback"
          + "/dot1q-cfm:input/dot1q-cfm:lbm-data-tlv" {
    description
      "Implementations compliant with ITU-T G.8021 are only required
       to support the configuration of the Data TLV Length
       (eth-oam:data-tlv-length).";
    reference
      "ITU-T G.8021 v8.1 (01/2024): clause 8.1.8";
    deviate not-supported;
  }

  deviation "/dot1q-cfm:cfm/dot1q-cfm:maintenance-group"
          + "/dot1q-cfm:mep/dot1q-cfm:transmit-loopback"
          + "/dot1q-cfm:output/dot1q-cfm:lbm-request-id" {
    description
      "Implementations compliant with ITU-T G.8021 are not requested
       to report the Transaction ID value is generated by the LB
       control discovery process (lbm-request-id).";
    reference
      "ITU-T G.8021 v8.1 (01/2024): clause 8.1.8";
    deviate not-supported;
  }

  deviation "/dot1q-cfm:cfm/dot1q-cfm:maintenance-group"
          + "/dot1q-cfm:mep/dot1q-cfm:transmit-linktrace"
          + "/dot1q-cfm:input/dot1q-cfm:ltr-target"
          + "/dot1q-cfm:target-mep-id" {
    description
      "Implementations compliant with ITU-T G.8021 are only required
       to support the configuration of the Target MAC address
       (ltm-target-mac-address).";
    reference
      "ITU-T G.8021 v8.1 (01/2024): clause 8.1.13";
    deviate not-supported;
  }

  deviation "/dot1q-cfm:cfm/dot1q-cfm:maintenance-group"
          + "/dot1q-cfm:mep/dot1q-cfm:transmit-linktrace"
          + "/dot1q-cfm:input/dot1q-cfm:ltm-flags" {
    description
      "Implementations compliant with ITU-T G.8021 not required to
       support the configuration of the ltm-flags.

       The Flag field of the transmitted LTM OAM Message is set by
       the system as specified in Figure 9.5-2 of ITU-T G.8013.";
    reference
      "ITU-T G.8021 v8.1 (01/2024): clause 8.1.13

       ITU-T G.8013 v6.1 (01/2024): figure 9.5-2";
    deviate not-supported;
  }

  deviation "/dot1q-cfm:cfm/dot1q-cfm:maintenance-group"
          + "/dot1q-cfm:mep/dot1q-cfm:transmit-linktrace"
          + "/dot1q-cfm:output/dot1q-cfm:ltm-transaction-id" {
    description
      "Implementations compliant with ITU-T G.8021 are not requested
       to report the Transaction ID value is generated by the LT
       control discovery process (ltm-transaction-id).";
    reference
      "ITU-T G.8021 v8.1 (01/2024): clause 8.1.13";
    deviate not-supported;
  }

  deviation "/dot1q-cfm:cfm/dot1q-cfm:maintenance-group"
          + "/dot1q-cfm:mep/dot1q-cfm:transmit-linktrace"
          + "/dot1q-cfm:output/dot1q-cfm:ltm-egress-identifier"
          + "/dot1q-cfm:int" {
    description
      "Implementations compliant with ITU-T G.8021 and with the 2006
       edition of ITU-T G.8013 are not required to support the LTM
       Egress Identifier TLV.";
    reference
      "ITU-T G.8021 v8.1 (01/2024): clause 8.1.13

       ITU-T G.8013 v6.1 (01/2024): annex B";
    deviate not-supported;
  }

  deviation "/dot1q-cfm:cfm/dot1q-cfm:maintenance-group"
          + "/dot1q-cfm:mep/dot1q-cfm:transmit-linktrace"
          + "/dot1q-cfm:output/dot1q-cfm:ltm-egress-identifier"
          + "/dot1q-cfm:address" {
    description
      "Implementations compliant with ITU-T G.8021 and with the 2006
       edition of ITU-T G.8013 are not required to support the LTM
       Egress Identifier TLV.";
    reference
      "ITU-T G.8021 v8.1 (01/2024): clause 8.1.13

       ITU-T G.8013 v6.1 (01/2024): annex B";
    deviate not-supported;
  }
}
