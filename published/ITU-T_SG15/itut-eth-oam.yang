module itut-eth-oam {
  yang-version 1.1;
  namespace "urn:itu:t:rec:eth-ne-oam:yang:itut-eth-oam";
  prefix eth-oam;

  import ietf-yang-types {
    prefix yang;
    reference
      "IETF RFC 6991";
  }
  import ieee802-types {
    prefix ieee;
    reference
      "IEEE Std 802.1Qcx-2020";
  }
  import ieee802-dot1q-types {
    prefix dot1q-types;
    reference
      "IEEE Std 802.1Qcx-2020";
  }
  import ieee802-dot1q-cfm-types {
    prefix cfm-types;
    reference
      "IEEE Std 802.1Qcx-2020";
  }
  import ieee802-dot1q-cfm {
    prefix dot1q-cfm;
    reference
      "IEEE Std 802.1Qcx-2020";
  }

  organization
    "ITU-T Study Group 15 (SG15) - International Telecommunication
     Union";
  contact
    "tsbsg15@itu.int";
  description
    "This module defines a YANG data model for configuring the
     Ethernet OAM capabilities defined in ITU-T G.8013 and
     ITU-T G.8021, augmenting the IEEE Connectivity Fault Management
     (CFM) YANG model.

     Copyright(C) ITU (2025).

     All rights reserved. This version of this YANG module is part of
     ITU-T G.8052.1 Operation, administration, maintenance (OAM)
     management information and data models for the
     Ethernet-transport network element; see the Recommendation
     itself for full legal notices.";
  reference
    "ITU-T G.8013 v6.1 (01/2024)

     ITU-T G.8021 v8.1 (01/2024)";

  revision 2025-06-13 {
    description
      "Added the support of the OAM Loopback (LB) and Link Trance
       (LT) maintenance functions.";
    reference
      "G.8052.1 v2.0 (06/2025)";
  }
  revision 2024-03-08 {
    description
      "Added support of PM threshold profiling, configuration of
       degrade defect detection, bandwidth notification and CSF OAM
       functions and clarified the behaviour of the measurement
       jobs.";
    reference
      "G.8052.1 v1.2 (03/2024)";
  }
  revision 2023-01-13 {
    description
      "Added support of on-demand measurement and proactive
       measurement.";
    reference
      "ITU-T G.8052.1 v1.1 (01/2023)";
  }
  revision 2021-01-13 {
    description
      "Initial version.";
    reference
      "ITU-T G.8052.1 v1.0 (01/2021)";
  }

  /*
   * Identities
   */

  identity oam-type {
    description
      "Base identity for the type of the OAM protocol.";
  }

  identity dual-ended-oam-type {
    base oam-type;
    description
      "Base identity for the type of the dual-ended OAM protocol.";
    reference
      "ITU-T G.8013 v6.1 (01/2024): clause 3.2.1";
  }

  identity oam-lm-ccm {
    base dual-ended-oam-type;
    description
      "Dual-ended CCM OAM protocol supporting loss measurement.";
    reference
      "ITU-T G.8013 v6.1 (01/2024): clause 9.2";
  }

  identity oam-1dm {
    base dual-ended-oam-type;
    description
      "Dual-ended 1DM OAM protocol.";
    reference
      "ITU-T G.8013 v6.1 (01/2024): clause 9.14";
  }

  identity oam-1sl {
    base dual-ended-oam-type;
    description
      "Dual-ended 1SL OAM protocol.";
    reference
      "ITU-T G.8013 v6.1 (01/2024): clause 9.24";
  }

  identity oam-tst {
    base dual-ended-oam-type;
    description
      "Dual-ended TST OAM protocol.";
    reference
      "ITU-T G.8013 v6.1 (01/2024): clause 9.9";
  }

  identity single-ended-oam-type {
    base oam-type;
    description
      "Base identity for the type of the dual-ended OAM protocol.";
    reference
      "ITU-T G.8013 v6.1 (01/2024): clause 3.2.19";
  }

  identity oam-lm-lmm {
    base single-ended-oam-type;
    description
      "Single-ended LMM/LMR OAM protocol.";
    reference
      "ITU-T G.8013 v6.1 (01/2024): clauses 9.12 and 9.13";
  }

  identity oam-dm {
    base single-ended-oam-type;
    description
      "Single-ended DMM/DMR OAM protocol.";
    reference
      "ITU-T G.8013 v6.1 (01/2024): clauses 9.15 and 9.16";
  }

  identity oam-sl {
    base single-ended-oam-type;
    description
      "Single-ended SLM/SLR OAM protocol.";
    reference
      "ITU-T G.8013 v6.1 (01/2024): clauses 9.22 and 9.23";
  }

  identity oam-tst-lbm {
    base single-ended-oam-type;
    description
      "Single-ended LBM/LBR OAM protocol supporting test.";
    reference
      "ITU-T G.8013 v6.1 (01/2024): clauses 9.3 and 9.4";
  }

  identity granularity-period {
    description
      "The base identity to define the Current Data and History Data
       Granularity Period (e.g., 15min/24h).";
    reference
      "ITU-T X.739 v1.2 (06/1998): clause 8.1.1.2";
  }

  identity granularity-period-24h {
    base granularity-period;
    description
      "24 Hours Granularity Period.";
    reference
      "ITU-T G.7710 v5.1 (11/2022): clause 10.1.6.1";
  }

  identity granularity-period-15min {
    base granularity-period;
    description
      "15 Minutes Granularity Period.";
    reference
      "ITU-T G.7710 v5.1 (11/2022): clause 10.1.6.1";
  }

  identity dm-period {
    description
      "Base identity for the periodicity of the
       DM (1DM or DMM/DMR) OAM messages.";
    reference
      "ITU-T G.8051 v6.2 (01/2024): Table 8-2";
  }

  identity dm-period-100ms {
    base dm-period;
    description
      "DM OAM messages are generated every 100 ms.";
  }

  identity dm-period-1sec {
    base dm-period;
    description
      "DM OAM messages are generated every second.";
  }

  identity dm-period-10sec {
    base dm-period;
    description
      "DM OAM messages are generated every 10 seconds.";
  }

  identity sl-period {
    description
      "Base identity for the periodicity of the
       SL (1SL or SLM/SLR) OAM messages.";
    reference
      "ITU-T G.8051 v6.2 (01/2024): Table 8-2";
  }

  identity sl-period-10ms {
    base sl-period;
    description
      "SL OAM messages are generated every 10 ms.";
  }

  identity sl-period-100ms {
    base sl-period;
    description
      "SL OAM messages are generated every 100 ms.";
  }

  identity sl-period-1sec {
    base sl-period;
    description
      "SL OAM messages are generated every second.";
  }

  identity sl-period-10sec {
    base sl-period;
    description
      "SL OAM messages are generated every 10 seconds.";
  }

  identity lm-period {
    description
      "Base identity for the periodicity of the
       LM (LMM/LMR) OAM messages.";
    reference
      "ITU-T G.8051 v6.2 (01/2024): Table 8-2";
  }

  identity lm-period-100ms {
    base lm-period;
    description
      "LM OAM messages are generated every 100 ms.";
  }

  identity lm-period-1sec {
    base lm-period;
    description
      "LM OAM messages are generated every second.";
  }

  identity lm-period-10sec {
    base lm-period;
    description
      "LM OAM messages are generated every 10 seconds.";
  }

  /*
   * Typedefs
   */

  typedef oam-type {
    type identityref {
      base oam-type;
    }
    description
      "The type of the OAM protocol.";
  }

  typedef dual-ended-oam-type {
    type identityref {
      base dual-ended-oam-type;
    }
    description
      "The type of the dual-ended OAM protocol.";
    reference
      "ITU-T G.8013 v6.1 (01/2024): clause 3.2.1";
  }

  typedef single-ended-oam-type {
    type identityref {
      base single-ended-oam-type;
    }
    description
      "The type of the single-ended OAM protocol.";
    reference
      "ITU-T G.8013 v6.1 (01/2024): clause 3.2.19";
  }

  typedef granularity-period {
    type identityref {
      base granularity-period;
    }
    description
      "The Current Data and History Data Granularity Period (e.g.,
       15min/24h).";
    reference
      "ITU-T X.739 v1.2 (06/1998): clause 8.1.1.2";
  }

  typedef ais-lck-period {
    type enumeration {
      enum 1sec {
        description
          "AIS or LCK OAM messages are generated every second.";
      }
      enum 1min {
        description
          "AIS or LCK OAM messages are generated every minute.";
      }
    }
    description
      "The periodicity of the AIS or LCK OAM messages.";
    reference
      "ITU-T G.8013 v6.1 (01/2024): table 9-4";
  }

  typedef dm-period {
    type identityref {
      base dm-period;
    }
    description
      "The periodicity of the DM (1DM or DMM/DMR) OAM messages.";
    reference
      "ITU-T G.8051 v6.2 (01/2024): Table 8-2";
  }

  typedef sl-period {
    type identityref {
      base sl-period;
    }
    description
      "The periodicity of the SL (1SL or SLM/SLR) OAM messages.";
    reference
      "ITU-T G.8051 v6.2 (01/2024): Table 8-2";
  }

  typedef lm-period {
    type identityref {
      base lm-period;
    }
    description
      "The periodicity of the LM (LMM/LMR) OAM messages.";
    reference
      "ITU-T G.8051 v6.2 (01/2024): Table 8-2";
  }

  typedef oam-pdu-generation-type {
    type enumeration {
      enum single-instance {
        description
          "A single instance of on-demand OAM message is
           generated.";
      }
      enum repetitive-instance {
        description
          "Repetitive instances of on-demand OAM message are
           generated.";
      }
      enum single-series {
        description
          "A single serie of on-demand OAM messages is generated.";
      }
      enum repetitive-series {
        description
          "Repetitive series of on-demand OAM messages are
           generated.";
      }
    }
    description
      "The generation pattern of the on-demand OAM messages.";
    reference
      "ITU-T G.8051 v6.2 (01/2024): clause 10.2";
  }

  typedef csf-config {
    type enumeration {
      enum disabled {
        description
          "The CSF generation process is disabled.";
      }
      enum enabled {
        description
          "The CSF generation process is enabled, but the client
           defect clear indication (C-DCI) and the reporting of the
           client reverse defect indication (C-RDI) and the forward
           defect indication (C-FDI) conditions are disabled.";
      }
      enum enabled-with-rdi-fdi {
        description
          "The CSF generation process and the reporting of the client
           reverse defect indication (C-RDI) and the forward defect
           indication (C-FDI) conditions are enabled, but the client
           defect clear indication (C-DCI) is disabled.";
      }
      enum enabled-with-rdi-fdi-dci {
        description
          "The CSF generation process; the client defect clear
           indication (C-DCI) and the reporting of the client reverse
           defect indication (C-RDI) and the forward defect
           indication (C-FDI) conditions are enabled.";
      }
      enum enabled-with-dci {
        description
          "The CSF generation process and the client defect clear
           indication (C-DCI) are enabled, but the reporting of the
           client reverse defect indication (C-RDI) and the forward
           defect indication (C-FDI) conditions is disabled.";
      }
    }
    description
      "This data type defines the configuration of the CSF generation
       process, describing whether the CSF generation process is
       enabled or disabled and, in case the process is enabled,
       whether the client defect clear indication (C-DCI) is also
       enabled or disabled and whether the reporting of the client
       reverse defect indication (C-RDI) and the forward defect
       indication (C-FDI) conditions is also enabled or disabled.";
    reference
      "ITU-T G.8021 v8.1 (01/2024): clause 8.1.16";
  }

  typedef csf-period {
    type enumeration {
      enum 1sec {
        description
          "CSF OAM messages are generated every second.";
      }
      enum 1min {
        description
          "CSF OAM messages are generated every minute.";
      }
    }
    description
      "The periodicity of the CSF OAM messages.";
    reference
      "ITU-T G.8013 v6.1 (01/2024): Table 9-6";
  }

  typedef test-pattern {
    type enumeration {
      enum null-without-crc-32 {
        value 0;
        description
          "Null signal without CRC-32.";
      }
      enum null-with-crc-32 {
        value 1;
        description
          "Null signal with CRC-32.";
      }
      enum prbs-31-without-crc-32 {
        value 2;
        description
          "PRBS-31 (2^-31 - 1) without CRC-32.";
      }
      enum prbs-31-with-crc-32 {
        value 3;
        description
          "PRBS-31 (2^-31 - 1) with CRC-32.";
      }
    }
    description
      "The test pattern of the Test (TST or LBM/LBR) OAM messages.";
    reference
      "ITU-T G.8013 v6.1 (01/2024): clause 9.3.2";
  }

  /*
   * Groupings
   */

  grouping current-data {
    description
      "The common attributes used by the performance monitoring
       Current Data.";
    reference
      "ITU-T Q.822 v1.1 (03/2003): clause 4.3.1.1";
    action reset-all-counters {
      description
        "Set all PM counters to zero and the suspect interval flag
         to True.";
    }
    leaf granularity-period {
      type granularity-period;
      mandatory true;
      description
        "The granularity period (e.g., 15min/24h) of the Current
         Data.";
      reference
        "ITU-T X.739 v1.2 (06/1998): clause 8.1.1.2";
    }
    container elapsed-time {
      config false;
      description
        "The difference between the current time and the start time
         of this current data.";
      reference
        "ITU-T Q.822 v1.1 (03/2003): clause 4.3.3.2";
      uses time-interval;
    }
    leaf suspect-interval-flag {
      type boolean;
      default "false";
      config false;
      description
        "The suspect interval flag.";
      reference
        "ITU-T Q.822 v1.1 (03/2003): clause 4.3.3.14";
    }
    leaf start-time {
      type yang:date-and-time;
      config false;
      mandatory true;
      description
        "The interval start time.

         The value is bound to the quarter of an hour in case of
         a 15 minute interval and bound to the hour in case of
         a 24 hour interval.";
    }
    leaf threshold-profile-ref {
      type leafref {
        path "/dot1q-cfm:cfm/eth-oam:threshold-profiles/"
           + "eth-oam:threshold-profile/"
           + "eth-oam:threshold-profile-id";
      }
      description
        "The pointer to the threshold profile associated with this
         current data.

         If not configured, a default threshold profile shall be
         assigned by the system.";
      reference
        "ITU-T G.7710 v5.1 (11/2022): clause 8.11";
    }
  }

  grouping dual-ended-current-data {
    description
      "The PM current data collected by a pro-active dual-ended
       measurement job.

       Note: this grouping has an external XPath references to
       ../oam-type.";
    uses current-data;
    container dm-data {
      when "derived-from-or-self(../../eth-oam:oam-type,
            'eth-oam:oam-1dm')" {
        description
          "When the OAM protocol is dual-ended 1DM.";
      }
      config false;
      description
        "The current pro-active delay measurement PM data.";
      uses pro-active-dual-ended-dm-current-data;
    }
    container lm-data {
      when "derived-from-or-self(../../eth-oam:oam-type,
            'eth-oam:oam-lm-ccm') or
            derived-from-or-self(../../eth-oam:oam-type,
            'eth-oam:oam-1sl')" {
        description
          "When the OAM protocol is dual-ended CCM or 1SL.";
      }
      config false;
      description
        "The current pro-active loss measurement PM data.";
      uses pro-active-dual-ended-lm-current-data;
    }
    list history-data {
      key "period-end-time";
      config false;
      description
        "The list of PM history data of a current data collected by a
         pro-active dual-ended measurement job.";
      uses history-data;
      container dm-data {
        when "derived-from-or-self(../../../eth-oam:oam-type,
              'eth-oam:oam-1dm')" {
          description
            "When the OAM protocol is dual-ended 1DM.";
        }
        config false;
        description
          "The history pro-active dual-ended delay measurement
           PM data.";
        uses pro-active-dual-ended-dm-history-data;
      }
      container lm-data {
        when "derived-from-or-self(../../../eth-oam:oam-type,
              'eth-oam:oam-lm-ccm') or
              derived-from-or-self(../../../eth-oam:oam-type,
              'eth-oam:oam-1sl')" {
          description
            "When the OAM protocol is dual-ended CCM or 1SL.";
        }
        config false;
        description
          "The history pro-active dual-ended loss measurement PM
           data.";
        uses pro-active-dual-ended-lm-history-data;
      }
    }
  }

  grouping single-ended-current-data {
    description
      "The PM current data collected by a pro-active single-ended
       measurement job.

       Note: this grouping has an external XPath references to
       ../oam-type.";
    uses current-data;
    container dm-data {
      when "derived-from-or-self(../../eth-oam:oam-type,
            'eth-oam:oam-dm')" {
        description
          "When the OAM protocol is single-ended DMM/DMR.";
      }
      config false;
      description
        "The current pro-active delay measurement PM data.";
      uses pro-active-single-ended-dm-current-data;
    }
    container lm-data {
      when "derived-from-or-self(../../eth-oam:oam-type,
            'eth-oam:oam-lm-lmm') or
            derived-from-or-self(../../eth-oam:oam-type,
            'eth-oam:oam-sl')" {
        description
          "When the OAM protocol is single-ended LMM/LMR or
           SLM/SLR.";
      }
      config false;
      description
        "The current pro-active loss measurement PM data.";
      uses pro-active-single-ended-lm-current-data;
    }
    list history-data {
      key "period-end-time";
      config false;
      description
        "The list of PM history data of a current data collected by a
         pro-active single-ended measurement job.";
      uses history-data;
      container dm-data {
        when "derived-from-or-self(../../../eth-oam:oam-type,
              'eth-oam:oam-dm')" {
          description
            "When the OAM protocol is single-ended DMM/DMR.";
        }
        config false;
        description
          "The history pro-active single-ended delay measurement PM
           data.";
        uses pro-active-single-ended-dm-history-data;
      }
      container lm-data {
        when "derived-from-or-self(../../../eth-oam:oam-type,
              'eth-oam:oam-lm-lmm') or
              derived-from-or-self(../../../eth-oam:oam-type,
              'eth-oam:oam-sl')" {
          description
            "When the OAM protocol is single-ended LMM/LMR or
             SLM/SLR.";
        }
        config false;
        description
          "The history pro-active single-ended loss measurement PM
           data.";
        uses pro-active-single-ended-lm-history-data;
      }
    }
  }

  grouping history-data {
    description
      "The common attributes used by the performance monitoring
       History Data.";
    reference
      "ITU-T Q.822 v1.1 (03/2003): clause 4.3.1.2";
    leaf period-end-time {
      type yang:date-and-time;
      config false;
      mandatory true;
      description
        "This attribute contains the time at the end
         of the interval.";
      reference
        "ITU-T Q.822 v1.1 (03/2003): clause 4.3.3.12";
    }
    leaf granularity-period {
      type granularity-period;
      config false;
      mandatory true;
      description
        "The granularity period (e.g., 15min/24h) of the History
         Data.";
      reference
        "ITU-T X.739 v1.2 (06/1998): clause 8.1.1.2";
    }
    leaf suspect-interval-flag {
      type boolean;
      default "false";
      config false;
      description
        "The suspect interval flag.";
      reference
        "ITU-T Q.822 v1.1 (03/2003): clause 4.3.3.14";
    }
  }

  grouping pro-active-dual-ended-mea-job-control-target {
    description
      "The attributes of a pro-active dual-ended
       measurement job control within a receiving MEP.

       When this OAM measurement job is enabled, the OAM PM process
       is running: the received OAM messages are processed and the
       PM data are collected and reported.

       When this OAM measurement job is disabled, the OAM PM process
       is stopped: the OAM PM process resources are still allocated
       but the received OAM messages are ignored and
       the PM data collected at the time the measurement job
       has been disabled are still reported; the current data
       suspect interval flag is set.";
    leaf oam-type {
      type dual-ended-oam-type;
      must "not(derived-from-or-self(current(),
            'eth-oam:oam-lm-ccm')) or count(/dot1q-cfm:cfm/
            dot1q-cfm:maintenance-domain[dot1q-cfm:md-id=current()/
            ../../../../../dot1q-cfm:md-id]/
            dot1q-cfm:maintenance-association[dot1q-cfm:ma-id=
            current()/../../../../../dot1q-cfm:ma-id]/
            dot1q-cfm:maintenance-association-mep)=2" {
        error-message "The dual-ended CCM OAM protocol "
                    + "(i.e., 'eth-oam:oam-lm-ccm'), can only be "
                    + "used for pro-active measurement jobs "
                    + "within point-to-point Maintenance Entity "
                    + "Groups (MEGs) (i.e., when the "
                    + "'/dot1q-cfm:cfm/"
                    + "dot1q-cfm:maintenance-domain/"
                    + "dot1q-cfm:maintenance-association/"
                    + "dot1q-cfm:maintenance-association-mep' "
                    + "list has only 2 elements).";
        description
          "The dual-ended CCM OAM protocol can only be used for
           pro-active measurement jobs within point-to-point
           Maintenance Entity Groups (MEGs).";
        reference
          "ITU-T G.8013 v6.1 (01/2024): clause 8.2.1";
      }
      mandatory true;
      description
        "The type of the dual-ended pro-active OAM protocol.";
    }
    uses pro-active-measurement-job-control;
    leaf source-address {
      when "not(derived-from-or-self(../eth-oam:oam-type,
            'eth-oam:oam-lm-ccm'))" {
        description
          "When the OAM protocol is not dual-ended CCM.";
      }
      type ieee:mac-address;
      mandatory true;
      description
        "The Unicast MAC address of the initiating MEP.";
    }
    container dm {
      when "derived-from-or-self(../eth-oam:oam-type,
            'eth-oam:oam-1dm')" {
        description
          "When the OAM protocol is dual-ended 1DM.";
      }
      description
        "Dual-ended 1DM OAM protocol configuration.";
      uses oam-dm-config-common;
    }
    container sl {
      when "derived-from-or-self(../eth-oam:oam-type,
            'eth-oam:oam-1sl')" {
        description
          "When the OAM protocol is dual-ended 1SL.";
      }
      description
        "Dual-ended 1SL OAM protocol configuration.";
      uses oam-sl-config-common;
    }
    list current-data {
      key "granularity-period";
      min-elements 1;
      description
        "The list of PM current data (one per granularity period)
         collected by a pro-active dual-ended measurement job.";
      uses dual-ended-current-data;
    }
  }

  grouping pro-active-dual-ended-mea-job-control-initiator {
    description
      "The attributes of a pro-active dual-ended
       measurement job control within an initiating MEP.

       When this OAM measurement job is enabled, the OAM PM process
       is running: the OAM messages are generated.

       When this OAM measurement job is disabled, the OAM PM process
       is stopped: the OAM PM process resources are still allocated,
       but OAM messages are not generated.";
    leaf oam-type {
      type dual-ended-oam-type;
      must "not(derived-from-or-self(current(),
            'eth-oam:oam-lm-ccm')) or count(/dot1q-cfm:cfm/
            dot1q-cfm:maintenance-domain[dot1q-cfm:md-id=current()/
            ../../../../../dot1q-cfm:md-id]/
            dot1q-cfm:maintenance-association[dot1q-cfm:ma-id=
            current()/../../../../../dot1q-cfm:ma-id]/
            dot1q-cfm:maintenance-association-mep)=2" {
        error-message "The dual-ended CCM OAM protocol "
                    + "(i.e., 'eth-oam:oam-lm-ccm'), can only be "
                    + "used for pro-active measurement jobs "
                    + "within point-to-point Maintenance Entity "
                    + "Groups (MEGs) (i.e., when the "
                    + "'/dot1q-cfm:cfm/"
                    + "dot1q-cfm:maintenance-domain/"
                    + "dot1q-cfm:maintenance-association/"
                    + "dot1q-cfm:maintenance-association-mep' "
                    + "list has only 2 elements).";
        description
          "The dual-ended CCM OAM protocol can only be used for
           pro-active measurement jobs within point-to-point
           Maintenance Entity Groups (MEGs).";
        reference
          "ITU-T G.8013 v6.1 (01/2024): clause 8.2.1";
      }
      mandatory true;
      description
        "The type of the dual-ended pro-active OAM protocol.";
    }
    uses pro-active-measurement-job-control;
    leaf destination-address {
      when "not(derived-from-or-self(../eth-oam:oam-type,
            'eth-oam:oam-lm-ccm'))" {
        description
          "When the OAM protocol is not dual-ended CCM.";
      }
      type ieee:mac-address;
      mandatory true;
      description
        "The Unicast MAC address of the target MEP.";
      reference
        "ITU-T G.8013 v6.1 (01/2024): clause 10";
    }
    container dm {
      when "derived-from-or-self(../eth-oam:oam-type,
            'eth-oam:oam-1dm')" {
        description
          "When the OAM protocol is dual-ended 1DM.";
      }
      description
        "Dual-ended 1DM OAM protocol configuration.";
      uses oam-dm-config;
    }
    container sl {
      when "derived-from-or-self(../eth-oam:oam-type,
            'eth-oam:oam-1sl')" {
        description
          "When the OAM protocol is dual-ended 1SL.";
      }
      description
        "Dual-ended 1SL OAM protocol configuration.";
      uses oam-sl-config;
    }
  }

  grouping pro-active-measurement-job-control {
    description
      "The common attributes of a pro-active
       measurement job control.";
    leaf enabled {
      type boolean;
      default "true";
      description
        "Enables the pro-active measurement job.";
    }
    leaf priority {
      type dot1q-types:priority-type;
      status deprecated;
      description
        "The priority value of the pro-active OAM messages.

         The default value is the same as the CCM priority.";
    }
  }

  grouping pro-active-single-ended-mea-job-control {
    description
      "The attributes of a pro-active single-ended
       measurement job control within an initiating MEP.

       When this OAM measurement job is enabled, the OAM PM process
       is running: the OAM messages are generated; the received OAM
       messages are processed and the PM data are collected and
       reported.

       When this OAM measurement job is disabled, the OAM PM process
       is stopped: the OAM PM process resources are still allocated
       but OAM messages are not generated; the received
       OAM messages are ignored and the PM data collected
       at the time the measurement job has been disabled
       are still reported; the current data
       suspect interval flag is set.";
    leaf oam-type {
      type single-ended-oam-type;
      must "not(derived-from-or-self(current(),
            'eth-oam:oam-lm-lmm')) or count(/dot1q-cfm:cfm/
            dot1q-cfm:maintenance-domain[dot1q-cfm:md-id=current()/
            ../../../../../dot1q-cfm:md-id]/
            dot1q-cfm:maintenance-association[dot1q-cfm:ma-id=
            current()/../../../../../dot1q-cfm:ma-id]/
            dot1q-cfm:maintenance-association-mep)=2" {
        error-message "The single-ended LMM/LMR OAM protocol "
                    + "(i.e.,'eth-oam:oam-lm-lmm') can only be "
                    + "used for measurement jobs within "
                    + "point-to-point Maintenance Entity Groups "
                    + "(MEGs) (i.e., when the '/dot1q-cfm:cfm/"
                    + "dot1q-cfm:maintenance-domain/"
                    + "dot1q-cfm:maintenance-association/"
                    + "dot1q-cfm:maintenance-association-mep' "
                    + "list has only 2 elements).";
        description
          "The single-ended LMM/LMR OAM protocol can only be used
           for measurement jobs within point-to-point Maintenance
           Entity Groups (MEGs).";
        reference
          "ITU-T G.8013 v6.1 (01/2024): clause 8.2.2";
      }
      mandatory true;
      description
        "The type of the single-ended pro-active OAM protocol.";
    }
    uses pro-active-measurement-job-control;
    leaf destination-address {
      type ieee:mac-address;
      mandatory true;
      description
        "The Unicast MAC address of the target MEP.";
      reference
        "ITU-T G.8013 v6.1 (01/2024): clause 10";
    }
    container dm {
      when "derived-from-or-self(../eth-oam:oam-type,
            'eth-oam:oam-dm')" {
        description
          "When the OAM protocol is single-ended DMM/DMR.";
      }
      description
        "Single-ended DMM/DMR OAM protocol configuration.";
      uses oam-dm-config;
    }
    container lm {
      when "derived-from-or-self(../eth-oam:oam-type,
            'eth-oam:oam-lm-lmm')" {
        description
          "When the OAM protocol is single-ended LMM/LMR.";
      }
      description
        "Single-ended LMM/LMR OAM protocol configuration.";
      uses oam-lm-config;
    }
    container sl {
      when "derived-from-or-self(../eth-oam:oam-type,
            'eth-oam:oam-sl')" {
        description
          "When the OAM protocol is single-ended SLM/SLR.";
      }
      description
        "Single-ended SLM/SLR OAM protocol configuration.";
      uses oam-sl-config;
    }
    list current-data {
      key "granularity-period";
      min-elements 1;
      description
        "The list of PM current data (one per granularity period)
         collected by a pro-active single-ended measurement job.";
      uses single-ended-current-data;
    }
  }

  grouping eth-mea-job-pac {
    description
      "The Measurement Job that is being performed by the MEP.";
    reference
      "ITU-T G.8051 v6.2 (01/2024): clause 10.2";
    leaf measurement-job-id {
      type string;
      description
        "The identifier of a measurement job instance.";
    }
    choice measurement-job-type {
      mandatory true;
      description
        "The type of the measurement job.";
      container pro-active-dual-ended {
        description
          "A pro-active dual-ended measurement job.";
        choice role {
          mandatory true;
          description
            "The role of the measurement job control.";
          container target {
            description
              "A pro-active dual-ended measurement job control
               within a receiving MEP.";
            uses pro-active-dual-ended-mea-job-control-target;
          }
          container initiator {
            description
              "A pro-active dual-ended measurement job control
               within an initiating MEP.";
            uses pro-active-dual-ended-mea-job-control-initiator;
          }
        }
      }
      container on-demand-dual-ended {
        description
          "An on-demand dual-ended measurement job.";
        choice role {
          mandatory true;
          description
            "The role of the measurement job control.";
          container target {
            description
              "An on-demand dual-ended measurement job control
               within a receiving MEP.";
            uses on-demand-dual-ended-mea-job-control-target;
          }
          container initiator {
            description
              "An on-demand dual-ended measurement job control
               within an initiating MEP.";
            uses on-demand-dual-ended-mea-job-control-initiator;
          }
        }
      }
      container pro-active-single-ended {
        description
          "A pro-active single-ended measurement job.";
        container control {
          description
            "A pro-active single-ended measurement job control
             within an initiating MEP.";
          uses pro-active-single-ended-mea-job-control;
        }
      }
      container on-demand-single-ended {
        description
          "An on-demand single-ended measurement job.";
        container control {
          description
            "An on-demand single-ended measurement job control
             within an initiating MEP.";
          uses on-demand-single-ended-mea-job-control;
        }
      }
    }
  }

  grouping eth-ais-lck-common {
    description
      "The common attributes for configuring AIS and LCK
       generation.";
    reference
      "ITU-T G.8021 v8.1 (01/2024): clauses 8.1.2 and 8.1.4";
    leaf period {
      type ais-lck-period;
      default "1sec";
      description
        "The AIS and LCK PDU generation period.";
      reference
        "ITU-T G.8013 v6.1 (01/2024): table 9-4";
    }
    leaf priority {
      type dot1q-types:priority-type;
      description
        "The priority value of the generated AIS/LCK messages.

         The default value is the same as the CCM priority.";
    }
  }

  grouping dm-performance-data {
    description
      "It contains the delay measurement performance data.";
    reference
      "ITU-T G.8051 v6.2 (01/2024): clause 10.2, item 19";
    leaf minimum-frame-delay {
      type uint64;
      units "nano-seconds";
      mandatory true;
      description
        "This attribute contains the minimum frame delay observed
         over the monitored period.";
    }
    leaf average-frame-delay {
      type uint64;
      units "nano-seconds";
      mandatory true;
      description
        "This attribute contains the average frame delay observed
         over the monitored period.";
    }
    leaf maximum-frame-delay {
      type uint64;
      units "nano-seconds";
      mandatory true;
      description
        "This attribute contains the maximum frame delay observed
         over the monitored period.";
    }
    leaf minimum-frame-delay-variation {
      type uint64;
      units "nano-seconds";
      mandatory true;
      description
        "This attribute contains the minimum frame delay variation
         observed over the monitored period.";
    }
    leaf average-frame-delay-variation {
      type uint64;
      units "nano-seconds";
      mandatory true;
      description
        "This attribute contains the average frame delay variation
         observed over the monitored period.";
    }
    leaf maximum-frame-delay-variation {
      type uint64;
      units "nano-seconds";
      mandatory true;
      description
        "This attribute contains the maximum frame delay variation
         observed over the monitored period.";
    }
  }

  grouping lm-performance-data {
    description
      "It contains the loss measurement performance data.";
    reference
      "ITU-T G.8051 v6.2 (01/2024): clause 10.2, item 17";
    leaf transmitted-frames {
      type uint64;
      config false;
      mandatory true;
      description
        "The total number of frames transmitted in the monitored
         period.";
    }
    leaf lost-frames {
      type uint64;
      config false;
      mandatory true;
      description
        "The total number of frames lost in the monitored
         period.";
    }
    leaf ses {
      type uint32 {
        range "0..86400";
      }
      units "seconds";
      config false;
      mandatory true;
      description
        "The total number of Severely Errored Seconds (SES)
         detected in the monitoring period.";
      reference
        "ITU-T G.7710 v5.1 (11/2022): clause 10.2";
    }
    leaf uas {
      type uint32 {
        range "0..86400";
      }
      units "seconds";
      config false;
      mandatory true;
      description
        "The total number of Unavailable Seconds (UAS) detected in
         the monitoring period.";
      reference
        "ITU-T G.7710 v5.1 (11/2022): clause 10.2";
    }
  }

  grouping time-interval {
    description
      "The attributes (e.g., hours, minutes) defining a time
       interval no longer than one month, with millisecond
       accuracy.";
    reference
      "ITU-T Q.821 v2.0 (02/2000): Annex A.7";
    leaf day {
      type uint64 {
        range "0..31";
      }
      default "0";
      description
        "The number of days in the time interval.";
    }
    leaf hour {
      type uint8 {
        range "0..23";
      }
      default "0";
      description
        "The number of hours in the time interval.";
    }
    leaf minute {
      type uint8 {
        range "0..59";
      }
      default "0";
      description
        "The number of minutes in the time interval.";
    }
    leaf second {
      type uint8 {
        range "0..59";
      }
      default "0";
      description
        "The number of seconds in the time interval.";
    }
    leaf msec {
      type uint16 {
        range "0..999";
      }
      default "0";
      description
        "The number of milliseconds in the time interval.";
    }
  }

  grouping pro-active-single-ended-dm-current-data {
    description
      "The pro-active single-ended delay measurement
       PM current data.

       Note: this grouping has an external XPath references to
       ../../oam-type.";
    container near-end-dm-data {
      when "derived-from-or-self(../../../eth-oam:oam-type,
            'eth-oam:oam-dm')" {
        description
          "When the OAM protocol is single-ended DMM/DMR.";
      }
      description
        "The pro-active near-end delay measurement PM data.";
      uses dm-performance-data;
    }
    container far-end-dm-data {
      when "derived-from-or-self(../../../eth-oam:oam-type,
            'eth-oam:oam-dm')" {
        description
          "When the OAM protocol is single-ended DMM/DMR.";
      }
      description
        "The pro-active far-end delay measurement PM data.";
      uses dm-performance-data;
    }
    container bidirectional-dm-data {
      when "derived-from-or-self(../../../eth-oam:oam-type,
            'eth-oam:oam-dm')" {
        description
          "When the OAM type is DMM/DMR.";
      }
      description
        "The pro-active bidirectional delay measurement PM data.";
      uses dm-performance-data;
    }
  }

  grouping pro-active-single-ended-dm-history-data {
    description
      "The pro-active single-ended delay measurement
       PM history data.

       Note: this grouping is intended to be the same as the
       grouping pro-active-single-ended-dm-current-data, but with an
       external XPath references to ../../../oam-type.";
    container near-end-dm-data {
      when "derived-from-or-self(../../../../eth-oam:oam-type,
            'eth-oam:oam-dm')" {
        description
          "When the OAM protocol is single-ended DMM/DMR.";
      }
      description
        "The pro-active near-end delay measurement PM data.";
      uses dm-performance-data;
    }
    container far-end-dm-data {
      when "derived-from-or-self(../../../../eth-oam:oam-type,
            'eth-oam:oam-dm')" {
        description
          "When the OAM protocol is single-ended DMM/DMR.";
      }
      description
        "The pro-active far-end delay measurement PM data.";
      uses dm-performance-data;
    }
    container bidirectional-dm-data {
      when "derived-from-or-self(../../../../eth-oam:oam-type,
            'eth-oam:oam-dm')" {
        description
          "When the OAM type is DMM/DMR.";
      }
      description
        "The pro-active bidirectional delay measurement PM data.";
      uses dm-performance-data;
    }
  } // pro-active-single-ended-dm-history-data

  grouping pro-active-single-ended-lm-current-data {
    description
      "The pro-active single-ended loss measurement
       PM current data.

       Note: this grouping has an external XPath references to
       ../../oam-type.";
    container near-end-lm-data {
      when "derived-from-or-self(../../../eth-oam:oam-type,
            'eth-oam:oam-lm-lmm') or
            derived-from-or-self(../../../eth-oam:oam-type,
            'eth-oam:oam-sl')" {
        description
          "When the OAM protocol is single-ended LMM/LMR or
           SLM/SLR.";
      }
      config false;
      description
        "The pro-active near-end loss measurement PM data.";
      uses lm-performance-data;
    }
    container far-end-lm-data {
      when "derived-from-or-self(../../../eth-oam:oam-type,
            'eth-oam:oam-lm-lmm') or
            derived-from-or-self(../../../eth-oam:oam-type,
            'eth-oam:oam-sl')" {
        description
          "When the OAM protocol is single-ended LMM/LMR or
           SLM/SLR.";
      }
      config false;
      description
        "The pro-active far-end loss measurement PM data.";
      uses lm-performance-data;
    }
    container bidirectional-lm-data {
      when "derived-from-or-self(../../../eth-oam:oam-type,
            'eth-oam:oam-lm-lmm') or
            derived-from-or-self(../../../eth-oam:oam-type,
            'eth-oam:oam-sl')" {
        description
          "When the OAM protocol is single-ended LMM/LMR or
           SLM/SLR.";
      }
      config false;
      description
        "The pro-active bidirectional loss measurement PM data.";
      uses lm-performance-data;
    }
  } // pro-active-single-ended-lm-current-data

  grouping pro-active-single-ended-lm-history-data {
    description
      "The pro-active single-ended loss measurement
       PM history data.

       Note: this grouping is intended to be the same as the
       grouping pro-active-single-ended-lm-current-data, but with an
       external XPath references to ../../../oam-type.";
    container near-end-lm-data {
      when "derived-from-or-self(../../../../eth-oam:oam-type,
            'eth-oam:oam-lm-lmm') or
            derived-from-or-self(../../../../eth-oam:oam-type,
            'eth-oam:oam-sl')" {
        description
          "When the OAM protocol is single-ended LMM/LMR or
           SLM/SLR.";
      }
      config false;
      description
        "The pro-active near-end loss measurement PM data.";
      uses lm-performance-data;
    }
    container far-end-lm-data {
      when "derived-from-or-self(../../../../eth-oam:oam-type,
            'eth-oam:oam-lm-lmm') or
            derived-from-or-self(../../../../eth-oam:oam-type,
            'eth-oam:oam-sl')" {
        description
          "When the OAM protocol is single-ended LMM/LMR or
           SLM/SLR.";
      }
      config false;
      description
        "The pro-active far-end loss measurement PM data.";
      uses lm-performance-data;
    }
    container bidirectional-lm-data {
      when "derived-from-or-self(../../../../eth-oam:oam-type,
            'eth-oam:oam-lm-lmm') or
            derived-from-or-self(../../../../eth-oam:oam-type,
            'eth-oam:oam-sl')" {
        description
          "When the OAM protocol is single-ended LMM/LMR or
           SLM/SLR.";
      }
      config false;
      description
        "The pro-active bidirectional loss measurement PM data.";
      uses lm-performance-data;
    }
  } // pro-active-single-ended-lm-history-data

  grouping pro-active-dual-ended-dm-current-data {
    description
      "The pro-active dual-ended delay measurement PM current data.

       Note: this grouping has an external XPath references to
       ../../oam-type.";
    container near-end-dm-data {
      when "derived-from-or-self(../../../eth-oam:oam-type,
            'eth-oam:oam-1dm')" {
        description
          "When the OAM protocol is dual-ended 1DM.";
      }
      description
        "The pro-active near-end delay measurement PM data.";
      uses dm-performance-data;
    }
  }

  grouping pro-active-dual-ended-dm-history-data {
    description
      "The pro-active dual-ended delay measurement PM history data.

       Note: this grouping is intended to be the same as the
       grouping pro-active-dual-ended-dm-current-data, but with an
       external XPath references to ../../../oam-type.";
    container near-end-dm-data {
      when "derived-from-or-self(../../../../eth-oam:oam-type,
            'eth-oam:oam-1dm')" {
        description
          "When the OAM protocol is dual-ended 1DM.";
      }
      description
        "The pro-active near-end delay measurement PM data.";
      uses dm-performance-data;
    }
  }

  grouping pro-active-dual-ended-lm-current-data {
    description
      "The pro-active dual-ended loss measurement PM current data.

       Note: this grouping has an external XPath references to
       ../../oam-type.";
    container near-end-lm-data {
      when "derived-from-or-self(../../../eth-oam:oam-type,
            'eth-oam:oam-lm-ccm') or
            derived-from-or-self(../../../eth-oam:oam-type,
            'eth-oam:oam-1sl')" {
        description
          "When the OAM protocol is dual-ended CCM or 1SL.";
      }
      config false;
      description
        "The pro-active near-end loss measurement PM data.";
      uses lm-performance-data;
    }
    container far-end-lm-data {
      when "derived-from-or-self(../../../eth-oam:oam-type,
            'eth-oam:oam-lm-ccm')" {
        description
          "When the OAM protocol is dual-ended CCM.";
      }
      config false;
      description
        "The pro-active far-end loss measurement PM data.";
      uses lm-performance-data;
    }
    container bidirectional-lm-data {
      when "derived-from-or-self(../../../eth-oam:oam-type,
            'eth-oam:oam-lm-ccm')" {
        description
          "When the OAM protocol is dual-ended CCM.";
      }
      config false;
      description
        "The pro-active bidirectional loss measurement PM data.";
      uses lm-performance-data;
    }
  } // grouping pro-active-dual-ended-lm-current-data

  grouping pro-active-dual-ended-lm-history-data {
    description
      "The pro-active dual-ended loss measurement PM history data.

       Note: this grouping is intended to be the same as the
       grouping pro-active-dual-ended-lm-current-data, but with an
       external XPath references to ../../../oam-type.";
    container near-end-lm-data {
      when "derived-from-or-self(../../../../eth-oam:oam-type,
            'eth-oam:oam-lm-ccm') or
            derived-from-or-self(../../../../eth-oam:oam-type,
            'eth-oam:oam-1sl')" {
        description
          "When the OAM protocol is dual-ended CCM or 1SL.";
      }
      config false;
      description
        "The pro-active near-end loss measurement PM data.";
      uses lm-performance-data;
    }
    container far-end-lm-data {
      when "derived-from-or-self(../../../../eth-oam:oam-type,
            'eth-oam:oam-lm-ccm')" {
        description
          "When the OAM protocol is dual-ended CCM.";
      }
      config false;
      description
        "The pro-active far-end loss measurement PM data.";
      uses lm-performance-data;
    }
    container bidirectional-lm-data {
      when "derived-from-or-self(../../../../eth-oam:oam-type,
            'eth-oam:oam-lm-ccm')" {
        description
          "When the OAM protocol is dual-ended CCM.";
      }
      config false;
      description
        "The pro-active bidirectional loss measurement PM data.";
      uses lm-performance-data;
    }
  }

  grouping ma-name-itu {
    description
      "The common attributes for the ITU-T MEG ID format.";
    reference
      "ITU-T G.8013 v6.1 (01/2024): annex A";
    leaf country-code {
      type string {
        length "2";
        pattern '[A-Z]*' {
          error-message "The country code (CC) may only consist "
                      + "of 2 alphabetic characters represented "
                      + "by uppercase letters (i.e., A-Z).";
          description
            "The country code (CC) is a string of 2 alphabetic
             characters represented by uppercase letters
             (i.e., A-Z).";
          reference
            "ITU-T G.8013 v6.1 (01/2024): clause A.2.";
        }
      }
      description
        "The Country Code (CC).

         It is present when the CC and ICC-based global
         MEG ID format is used and not present when the ICC-based
         MEG ID format is used.";
    }
    leaf carrier-code {
      type string {
        length "1..6";
        pattern '[0-9A-Z]*' {
          error-message "The ITU Carrier Code (ICC) may only "
                      + "consist of alphabetic (i.e., A-Z) or "
                      + "numeric (i.e., 0-9) characters.";
          description
            "The ITU Carrier Code (ICC) is a string of 1-6
             alphabetic (i.e., A-Z) or numeric (i.e., 0-9)
             characters.";
          reference
            "ITU-T G.8013 v6.1 (01/2024): clauses A.1 and A.2.";
        }
      }
      mandatory true;
      description
        "The ITU Carrier Code (ICC).";
    }
    leaf meg-id-code {
      type string {
        length "1..12";
      }
      must "boolean(../eth-oam:country-code) or
            (string-length() +
            string-length(../eth-oam:carrier-code) <= 13)" {
        error-message "When defining an ICC-based MEG ID value "
                    + "(i.e., no 'country-code' is defined), the "
                    + "combined string length of the "
                    + "'carrier-code' (i.e., the ITU Carrier Code "
                    + "(ICC)) and of the 'meg-id-code' (i.e. the "
                    + "Unique MEG ID Code (UMC)) shall not exceed "
                    + "13 characters.";
        description
          "When defining an ICC-based MEG ID, the combined length
           of the ITU Carrier Code (ICC) and of the Unique MEG ID
           Code (UMC) subfields does not exceed 13 characters.";
        reference
          "ITU-T G.8013 v6.1 (01/2024): Figure A.3";
      }
      must "not(boolean(../eth-oam:country-code)) or
            (string-length(../eth-oam:carrier-code) = 6) or
            (string-length(../eth-oam:carrier-code) < 6 and
            (string-length() +
            string-length(../eth-oam:carrier-code) <= 12))" {
        error-message "When defining a CC and ICC-based MEG ID "
                    + "value (i.e., the 'country-code' is defined) "
                    + "with an ITU Carrier Code (ICC) that is less "
                    + "than 6 characters, the combined length of "
                    + "the 'carrier-code' (i.e., the ICC) and of "
                    + "the 'meg-id-code' (i.e. the Unique MEG ID "
                    + "Code (UMC) without the leading '/' "
                    + "character) shall not exceed 12 characters.";
        description
          "When defining a CC and ICC-based MEG ID, with an ITU
           Carrier Code (ICC) that is less than 6 characters, the
           combined length of the ICC and of the Unique MEG ID Code
           (UMC) subfields, excluding the UMC leading '/' character,
           does not exceed 12 characters.";
        reference
          "ITU-T G.8013 v6.1 (01/2024): Figure A.5";
      }
      must "not(boolean(../eth-oam:country-code)) or
            (string-length(../eth-oam:carrier-code) < 6) or
            (string-length(../eth-oam:carrier-code) = 6 and
            (string-length() <= 7))" {
        error-message "When defining a CC and ICC-based MEG ID "
                    + "value (i.e., the 'country-code' is defined) "
                    + "with an ITU Carrier Code (ICC), that is 6 "
                    + "characters long, the length of the "
                    + "'meg-id-code' (i.e. the Unique MEG ID "
                    + "(UMC)) shall not exceed 7 characters.";
        description
          "When defining an CC and ICC-based MEG ID, with an ITU
           Carrier Code (ICC) that is 6 characters long, the length
           of the Unique MEG ID Code (UMC) subfield does not exceed
           7 characters.";
        reference
          "ITU-T G.8013 v6.1 (01/2024): Figure A.5";
      }
      mandatory true;
      description
        "The Unique MEG ID code (UMC), excluding the trailing NULLs.

         When the MEG ID is using the CC and ICC-based MEG ID format
         and the ICC is less than 6 characters, the UMC leading '/'
         character is also excluded.";
    }
  }

  grouping oam-dm-config-common {
    description
      "Common attributes used for Delay Measurement OAM protocol
       (1DM or DMM/DMR) configuration.";
    reference
      "ITU-T G.8013 v6.1 (01/2024): clauses 9.14, 9.15 and 9.16";
    leaf priority {
      type dot1q-types:priority-type;
      description
        "The priority value of the DM (1DM or DMM/DMR) OAM messages.

         The default value is the same as the CCM priority.";
    }
    leaf test-identifier {
      type uint32;
      description
        "The value of the Test ID field within the optional
         Test ID TLV.

         If not specified, the Test ID TLV is not included
         in the OAM messages.";
    }
  }

  grouping oam-dm-config {
    description
      "Delay Measurement OAM protocol (1DM or DMM/DMR)
       configuration.";
    reference
      "ITU-T G.8013 v6.1 (01/2024): clauses 9.14, 9.15 and 9.16";
    uses oam-dm-config-common;
    leaf period {
      type dm-period;
      default "dm-period-100ms";
      description
        "The periodicity of the DM (1DM or DMM/DMR) OAM messages.";
      reference
        "ITU-T G.8051 v6.2 (01/2024): Table 8-2";
    }
    leaf data-tlv-length {
      type uint16;
      description
        "The Length of the optional Data TLV to be inserted in the
         OAM PDU.

         When configuring this value, care must be taken to avoid
         exceeding the maximum frame size limitations.

         If not specified, the Data TLV is not included
         in the OAM messages.";
    }
  }

  grouping oam-sl-config-common {
    description
      "Common attributes used for Synthetic Loss Measurement OAM
       protocol (1SL or SLM/SLR) configuration.";
    reference
      "ITU-T G.8013 v6.1 (01/2024): clauses 9.22, 9.23 and 9.24";
    leaf priority {
      type dot1q-types:priority-type;
      description
        "The priority value of the SL (1SL or SLM/SLR) OAM messages.

         The default value is the same as the CCM priority.";
    }
    leaf test-identifier {
      type uint32;
      mandatory true;
      description
        "The value of the Test ID field.";
    }
  }

  grouping oam-sl-config {
    description
      "Synthetic Loss Measurement OAM protocol (1SL or SLM/SLR)
       configuration.";
    reference
      "ITU-T G.8013 v6.1 (01/2024): clause 9.22, 9.23 and 9.24";
    uses oam-sl-config-common;
    leaf period {
      type sl-period;
      default "sl-period-100ms";
      description
        "The periodicity of the SL (1SL or SLM/SLR) OAM messages.";
      reference
        "ITU-T G.8051 v6.2 (01/2024): Table 8-2";
    }
    leaf data-tlv-length {
      type uint16;
      description
        "The Length of the optional Data TLV to be inserted in the
         OAM PDU.

         When configuring this value, care must be taken to avoid
         exceeding the maximum frame size limitations.

         If not specified, the Data TLV is not included
         in the OAM messages.";
    }
  }

  grouping oam-lm-config {
    description
      "Loss Measurement OAM protocol (LMM/LMR) configuration.";
    reference
      "ITU-T G.8013 v6.1 (01/2024): clauses 9.12 and 9.13";
    leaf priority {
      type dot1q-types:priority-type;
      description
        "The priority value of the LM (LMM/LMR) OAM messages.

         The default value is the same as the CCM priority.";
    }
    leaf period {
      type lm-period;
      default "lm-period-100ms";
      description
        "The periodicity of the LM (LMM/LMR) OAM messages.";
      reference
        "ITU-T G.8051 v6.2 (01/2024): Table 8-2";
    }
  }

  grouping oam-test-config-common {
    description
      "Common attributes used for Test OAM protocol (TST or LBM/LBR)
       configuration.";
    reference
      "ITU-T G.8013 v6.1 (01/2024): clause 9.3, 9.4 and 9.9";
    leaf test-tlv-pattern {
      type test-pattern;
      description
        "The pattern of the optional Test TLV to be inserted in the
         Test (TST or LBM/LBR) OAM messages.

         If not specified, the Test TLV is not included in the OAM
         messages.";
    }
  }

  grouping oam-test-config {
    description
      "Test OAM protocol (TST or LBM/LBR) configuration.";
    reference
      "ITU-T G.8013 v6.1 (01/2024): clause 9.3, 9.4 and 9.9";
    leaf priority {
      type dot1q-types:priority-type;
      description
        "The priority value of the Test (TST or LBM/LBR) OAM
         messages.

         The default value is the same as the CCM priority.";
    }
    leaf drop-eligible {
      type boolean;
      default "false";
      description
        "The Drop Eligibility (DE) of the Test (TST or LBM/LBR)
         OAM messages.

         A value 'true' means that the OAM message is Drop Eligible
         while a value 'false' means that the OAM message is not
         Drop Eligible.";
    }
    leaf period {
      type uint32;
      units "milliseconds";
      description
        "The periodicity of the Test (TST or LBM/LBR) OAM messages.

         The default value, the value range and the granularity of
         the values within the value range are implementation
         specific.";
    }
    uses oam-test-config-common;
    leaf test-tlv-length {
      when '../test-tlv-pattern' {
        description
          "When the optional Test TLV is to be inserted in the Test
           (TST or LBM/LBR) OAM messages.";
      }
      type uint16;
      description
        "The Length of the optional Test TLV to be inserted in the
         Test (TST or LBM/LBR) OAM messages.

         When configuring this value, care must be taken to avoid
         exceeding the maximum frame size limitations.

         The default value is implementation specific.";
    }
  }

  grouping dm-result {
    description
      "The results of an on-demand delay measurement job.";
    reference
      "ITU-T G.8051 v6.2 (01/2024): clause 10.2";
    leaf number-of-samples {
      type uint16;
      config false;
      mandatory true;
      description
        "The number of received DM messages received in the
         measurement interval.";
    }
    leaf-list frame-delay {
      type uint64;
      units "nanoseconds";
      config false;
      description
        "The list of frame delay measurements, reported in
         chronological order starting from the less recent.

         The multiplicity is defined by the number-of-samples
         attribute.";
    }
    leaf-list frame-delay-variation {
      type int64;
      units "nanoseconds";
      config false;
      description
        "The list of frame delay variation measurements, reported in
         chronological order starting from the less recent.

         The multiplicity is defined by (number-of-samples - 1),
         for number-of-samples > 0; or 0 otherwise.";
    }
  }

  grouping lm-result {
    description
      "The results of an on-demand loss measurement job.";
    reference
      "ITU-T G.8051 v6.2 (01/2024): clause 10.2";
    leaf transmitted-frames {
      type uint64;
      config false;
      mandatory true;
      description
        "The total number of frames transmitted in the measurement
         interval.";
    }
    leaf lost-frames {
      type uint64;
      config false;
      mandatory true;
      description
        "The total number of frames lost in the measurement
         interval.";
    }
  }

  grouping test-result-sender {
    description
      "The results of a diagnostic test reported by the sender of the
       Test (TST or LBM) OAM messages.";
    reference
      "ITU-T G.8021 v8.1 (01/2024): clauses 8.1.8.1 and 8.1.12.2";
    leaf sent {
      type uint64;
      config false;
      mandatory true;
      description
        "Number of Test (TST or LBM) OAM messages which have been
         sent.";
    }
  }

  grouping test-result-receiver {
    description
      "The results of a diagnostic test reported by the receiver of
       the Test (TST or LBR) OAM messages.";
    reference
      "ITU-T G.8021 v8.1 (01/2024): clauses 8.1.8.1 and 8.1.12.3";
    leaf received {
      type uint64;
      config false;
      mandatory true;
      description
        "Number of Test (TST or LBR) OAM messages which have been
         received.";
    }
    leaf crc-error {
      type uint64;
      config false;
      description
        "Number of received Test (TST or LBR) OAM messages where
         the Cyclic Redundancy Check (CRC) in the pattern failed.

         This attribute shall be reported when and only when the CRC
         pattern is included in the Test (TST or LBM/LBR) OAM
         messages.";
    }
    leaf ber {
      type uint64;
      config false;
      mandatory true;
      description
        "Number of received Test (TST or LBR) OAM messages where
         there was a bit error in the pattern.";
    }
    leaf out-of-order {
      type uint64;
      config false;
      mandatory true;
      description
        "Number of Test (TST or LBR) OAM messages which have been
         received out of order.";
    }
  }

  grouping dual-ended-pm-report {
    description
      "The report of a measurement interval of a dual-ended
       on-demand measurement job.

       Note: this grouping has an external XPath references to
       ../oam-type.";
    reference
      "ITU-T G.8051 v6.2 (01/2024): clause 10.2";
    leaf time-stamp {
      type yang:date-and-time;
      mandatory true;
      description
        "The time when the PM report has been generated.";
    }
    container lm-data {
      when "derived-from-or-self(../../eth-oam:oam-type,
            'eth-oam:oam-1sl')" {
        description
          "When the OAM protocol is dual-ended 1SL.";
      }
      description
        "The on-demand loss measurement PM data report.";
      container near-end-lm-data {
        description
          "The near-end loss measurement PM results.";
        uses lm-result;
      }
    }
    container dm-data {
      when "derived-from-or-self(../../eth-oam:oam-type,
            'eth-oam:oam-1dm')" {
        description
          "When the OAM protocol is dual-ended 1DM.";
      }
      description
        "The on-demand delay measurement PM data report.";
      container near-end-dm-data {
        description
          "The near-end delay measurement PM results.";
        uses dm-result;
      }
    }
    container test-data {
      when "derived-from-or-self(../../eth-oam:oam-type,
            'eth-oam:oam-tst')" {
        description
          "When the OAM protocol is dual-ended TST.";
      }
      description
        "The unidirectional diagnostic test results at the
         target MEP.";
      uses test-result-receiver;
    }
  }

  grouping dual-ended-pm-intermediate-report {
    description
      "The intermediate report of a measurement interval of a
       dual-ended on-demand measurement job.

       Note: this grouping is intended to be the same as the
       grouping dual-ended-pm-report, but with an
       external XPath references to ../../oam-type.";
    reference
      "ITU-T G.8051 v6.2 (01/2024): clause 10.2";
    leaf time-stamp {
      type yang:date-and-time;
      mandatory true;
      description
        "The time when the PM report has been generated.";
    }
    container lm-data {
      when "derived-from-or-self(../../../eth-oam:oam-type,
            'eth-oam:oam-1sl')" {
        description
          "When the OAM protocol is dual-ended 1SL.";
      }
      description
        "The on-demand loss measurement PM data report.";
      container near-end-lm-data {
        description
          "The near-end loss measurement PM results.";
        uses lm-result;
      }
    }
    container dm-data {
      when "derived-from-or-self(../../../eth-oam:oam-type,
            'eth-oam:oam-1dm')" {
        description
          "When the OAM protocol is dual-ended 1DM.";
      }
      description
        "The on-demand delay measurement PM data report.";
      container near-end-dm-data {
        description
          "The near-end delay measurement PM results.";
        uses dm-result;
      }
    }
  }

  grouping single-ended-pm-report {
    description
      "The report of a measurement interval of a single-ended
       on-demand measurement job.

       Note: this grouping has an external XPath references to
       ../oam-type.";
    reference
      "ITU-T G.8051 v6.2 (01/2024): clause 10.2";
    leaf time-stamp {
      type yang:date-and-time;
      description
        "The time when the PM report has been generated.";
    }
    container dm-data {
      when "derived-from-or-self(../../eth-oam:oam-type,
            'eth-oam:oam-dm')" {
        description
          "When the OAM protocol is single-ended DMM/DMR.";
      }
      description
        "The on-demand delay measurement PM data report.";
      container near-end-dm-data {
        description
          "The near-end delay measurement PM results.";
        uses dm-result;
      }
      container far-end-dm-data {
        description
          "The far-end delay measurement PM results.";
        uses dm-result;
      }
      container bidirectional-dm-data {
        description
          "The bidirectional delay measurement PM results.";
        uses dm-result;
      }
    }
    container lm-data {
      when "derived-from-or-self(../../eth-oam:oam-type,
            'eth-oam:oam-lm-lmm') or derived-from-or-self
            (../../eth-oam:oam-type, 'eth-oam:oam-sl')" {
        description
          "When the OAM protocol is single-ended LMM/LMR or
           single-ended SLM/SLR.";
      }
      description
        "The on-demand loss measurement PM data report.";
      container near-end-lm-data {
        description
          "The near-end loss measurement PM results.";
        uses lm-result;
      }
      container far-end-lm-data {
        description
          "The far-end loss measurement PM results.";
        uses lm-result;
      }
    }
    container test-data {
      when "derived-from-or-self(../../eth-oam:oam-type,
            'eth-oam:oam-tst-lbm')" {
        description
          "When the OAM protocol is single-ended LBM/LBR.";
      }
      description
        "The bidirectional diagnostic test results.";
      uses test-result-sender;
      uses test-result-receiver;
    }
  }

  grouping single-ended-pm-intermediate-report {
    description
      "The report of a measurement interval of a single-ended
       on-demand measurement job.

       Note: this grouping is intended to be the same as the
       grouping single-ended-pm-report, but with an
       external XPath references to ../../oam-type.";
    reference
      "ITU-T G.8051 v6.2 (01/2024): clause 10.2";
    leaf time-stamp {
      type yang:date-and-time;
      description
        "The time when the PM report has been generated.";
    }
    container dm-data {
      when "derived-from-or-self(../../../eth-oam:oam-type,
            'eth-oam:oam-dm')" {
        description
          "When the OAM protocol is single-ended DMM/DMR.";
      }
      description
        "The on-demand delay measurement PM data report.";
      container near-end-dm-data {
        description
          "The near-end delay measurement PM results.";
        uses dm-result;
      }
      container far-end-dm-data {
        description
          "The far-end delay measurement PM results.";
        uses dm-result;
      }
      container bidirectional-dm-data {
        description
          "The bidirectional delay measurement PM results.";
        uses dm-result;
      }
    }
    container lm-data {
      when "derived-from-or-self(../../../eth-oam:oam-type,
            'eth-oam:oam-lm-lmm') or derived-from-or-self
            (../../../eth-oam:oam-type, 'oam-sl')" {
        description
          "When the OAM protocol is single-ended LMM/LMR or
           single-ended SLM/SLR.";
      }
      description
        "The on-demand loss measurement PM data report.";
      container near-end-lm-data {
        description
          "The near-end loss measurement PM results.";
        uses lm-result;
      }
      container far-end-lm-data {
        description
          "The far-end loss measurement PM results.";
        uses lm-result;
      }
    }
  }

  grouping on-demand-dual-ended-mea-job-control-target {
    description
      "The attributes of an on-demand dual-ended measurement job
       control within a receiving MEP.

       If the start time is not reached yet, the OAM PM process is
       not running: the OAM PM resources are allocated but any
       received OAM message is ignored and no PM data is reported.

       After the start time is reached; if the stop time is not
       reached yet, the OAM PM process may be running or not running
       and some PM data may be reported, based on the behavior of
       the configured OAM PDU generation type.

       If the stop time is reached, the OAM PM process is stopped:
       the OAM PM process resources are still allocated but any
       received OAM message is ignored, and the PM data collected at
       the time the measurement job has been stopped are still
       reported.

       If the measurement job is requested to be deleted before the
       stop time is reached: the ongoing OAM PM process is stopped,
       the OAM PM process resources are released, and then the
       measurement job is deleted, including all of its reports.

       If the measurement job is requested to be deleted after the
       stop time is reached: the OAM PM process resources are
       released, and then the measurement job is deleted, including
       all of its reports.";
    reference
      "ITU-T G.8051 v6.2 (01/2024): clause 10.2";
    action get-intermediate-report {
      description
        "This operation requests an intermediate PM data report
         of the on-going dual-ended measurement interval.

         Intermediate means before the scheduled end of the
         measurement interval.

         If the request is received during the gap between two
         measurement intervals or at the end of a measurement
         interval, the report of the latest measurement interval is
         reported (with the same timestamp).

         If the request is received before the start-time, an error
         is reported.";
      output {
        container intermediate-report {
          presence
            "This container is present when the report is available
             (i.e., after the measurement job start-time)";
          description
            "Returns the requested intermediate PM data report of the
             on-going dual-ended measurement interval, if
             available.";
          uses dual-ended-pm-intermediate-report;
        }
      }
    }
    leaf oam-type {
      type dual-ended-oam-type;
      must "not(derived-from-or-self(current(),
            'eth-oam:oam-lm-ccm'))" {
        error-message "The dual-ended CCM OAM protocol (i.e., "
                    + "'eth-oam:oam-lm-ccm'), can only be used for "
                    + "pro-active measurement jobs.";
        description
          "The dual-ended CCM OAM protocol can only be used for
           pro-active measurement jobs.";
        reference
          "ITU-T G.8013 v6.1 (01/2024): clause 8.2.1";
      }
      must "derived-from-or-self(current(),'eth-oam:oam-1dm') or
            (../eth-oam:oam-pdu-generation-type='single-series') or
            (../eth-oam:oam-pdu-generation-type='repetitive-series')
           " {
        error-message "The single instance (i.e., "
                    + "'single-instance') and repetitive instance "
                    + "(i.e., 'repetitive-instance') OAM PDU "
                    + "generation types (i.e., "
                    + "'eth-oam:oam-pdu-generation-type') are "
                    + "applicable only to dual-ended 1DM OAM "
                    + "protocol type (i.e., 'eth-oam:oam-1dm').";
        description
          "The single instance and repetitive instance OAM PDU
           generation types are applicable only to dual-ended 1DM OAM
           protocol type.";
      }
      mandatory true;
      description
        "The type of the dual-ended on-demand OAM protocol.";
    }
    uses on-demand-measurement-job-control;
    leaf source-address {
      type ieee:mac-address;
      mandatory true;
      description
        "The Unicast MAC address of the initiating MEP.";
    }
    container dm {
      when "derived-from-or-self(../eth-oam:oam-type,
            'eth-oam:oam-1dm')" {
        description
          "When the OAM protocol is dual-ended 1DM.";
      }
      description
        "Dual-ended 1DM OAM protocol configuration.";
      uses oam-dm-config-common;
    }
    container sl {
      when "derived-from-or-self(../eth-oam:oam-type,
            'eth-oam:oam-1sl')" {
        description
          "When the OAM protocol is dual-ended 1SL.";
      }
      description
        "Dual-ended 1SL OAM protocol configuration.";
      uses oam-sl-config-common;
    }
    container test {
      when "derived-from-or-self(../eth-oam:oam-type,
            'eth-oam:oam-tst')" {
        description
          "When the OAM protocol is dual-ended TST.";
      }
      description
        "Dual-ended TST OAM protocol configuration.";
      uses oam-test-config-common;
    }
    list report {
      key "time-stamp";
      config false;
      description
        "The list of reports, one for each measurement interval, of
         the on-demand PM measurement job.

         A report is created at the end of a measurement interval
         when the results are ready to be reported.

         When the start time is reached, the list of the existing
         reports, if any, is emptied out.";
      uses dual-ended-pm-report;
    }
  }

  grouping on-demand-dual-ended-mea-job-control-initiator {
    description
      "The attributes of an on-demand dual-ended measurement job
       control within an initiating MEP.

       If the start time is not reached yet, the OAM PM process is
       not running: the OAM PM resources are allocated but the OAM
       messages are not generated.

       After the start time is reached; if the stop time is not
       reached yet, the OAM PM process may be running or not running,
       based on the behaviour of the configured OAM PDU generation
       type.

       If the stop time is reached, the OAM PM process is stopped:
       the OAM PM process resources are still allocated but OAM
       messages are not generated.

       If the measurement job is requested to be deleted before the
       stop time is reached: the ongoing OAM PM process is stopped,
       the OAM PM process resources are released, and then the
       measurement job is deleted.

       If the measurement job is requested to be deleted after the
       stop time is reached: the OAM PM process resources are
       released, and then the measurement job is deleted.";
    reference
      "ITU-T G.8051 v6.2 (01/2024): clause 10.2";
    leaf oam-type {
      type dual-ended-oam-type;
      must "not(derived-from-or-self(current(),
            'eth-oam:oam-lm-ccm'))" {
        error-message "The dual-ended CCM OAM protocol "
                    + "(i.e., 'eth-oam:oam-lm-ccm'), can only be "
                    + "used for pro-active measurement jobs.";
        description
          "The dual-ended CCM OAM protocol can only be used for
           pro-active measurement jobs.";
        reference
          "ITU-T G.8013 v6.1 (01/2024): clause 8.2.1";
      }
      must "derived-from-or-self(current(),'eth-oam:oam-1dm') or
            (../eth-oam:oam-pdu-generation-type='single-series') or
            (../eth-oam:oam-pdu-generation-type='repetitive-series')
           " {
        error-message "The single instance "
                    + "(i.e., 'single-instance') and repetitive "
                    + "instance (i.e., 'repetitive-instance') OAM "
                    + "PDU generation types "
                    + "(i.e., 'eth-oam:oam-pdu-generation-type') "
                    + "are applicable only to dual-ended 1DM OAM "
                    + "protocol type (i.e., 'eth-oam:oam-1dm').";
        description
          "The single instance and repetitive instance OAM PDU
           generation types are applicable only to dual-ended 1DM OAM
           protocol type.";
      }
      mandatory true;
      description
        "The type of the dual-ended on-demand OAM protocol.";
    }
    uses on-demand-measurement-job-control;
    leaf destination-address {
      type ieee:mac-address;
      mandatory true;
      description
        "The Unicast MAC address of the target MEP.";
    }
    container dm {
      when "derived-from-or-self(../eth-oam:oam-type,
            'eth-oam:oam-1dm')" {
        description
          "When the OAM protocol is dual-ended 1DM.";
      }
      description
        "Dual-ended 1DM OAM protocol configuration.";
      uses oam-dm-config;
    }
    container sl {
      when "derived-from-or-self(../eth-oam:oam-type,
            'eth-oam:oam-1sl')" {
        description
          "When the OAM protocol is dual-ended 1SL.";
      }
      description
        "Dual-ended 1SL OAM protocol configuration.";
      uses oam-sl-config;
    }
    container test {
      when "derived-from-or-self(../eth-oam:oam-type,
            'eth-oam:oam-tst')" {
        description
          "When the OAM protocol is dual-ended TST.";
      }
      description
        "Dual-ended TST OAM protocol configuration.";
      uses oam-test-config;
    }
    list report {
      key "time-stamp";
      config false;
      description
        "The list of reports, one for each measurement interval,
         of the on-demand PM measurement job at the initiator MEP.

         A report is created at the end of a measurement interval
         when the results are ready to be reported.

         When the start time is reached, the list of the existing
         reports, if any, is emptied out.";
      leaf time-stamp {
        type yang:date-and-time;
        description
          "The time when the PM report has been generated.";
      }
      container test-data {
        when "derived-from-or-self(../../eth-oam:oam-type,
              'eth-oam:oam-tst')" {
          description
            "When the OAM protocol is dual-ended TST.";
        }
        description
          "The unidirectional diagnostic test results at the
           initiator MEP.";
        uses test-result-sender;
      }
    }
  }

  grouping on-demand-single-ended-mea-job-control {
    description
      "The attributes of an on-demand single-ended measurement job
       control within an initiating MEP.

       If the start time is not reached yet, the OAM PM process is
       not running: the OAM PM resources are allocated but the OAM
       messages are not generated; any received OAM message is
       ignored and no PM data is reported.

       After the start time is reached; if the stop time is not
       reached yet, the OAM PM process may be running or not running
       and some PM data may be reported, based on the behaviour of
       the configured OAM PDU generation type.

       If the stop time is reached, the OAM PM process is stopped:
       the OAM PM process resources are still allocated but OAM
       messages are not generated; any received OAM message is
       ignored, and the PM data collected at the time the measurement
       job has been stopped are still reported.

       If the measurement job is requested to be deleted before the
       stop time is reached: the ongoing OAM PM process is stopped,
       the OAM PM process resources are released, and then the
       measurement job is deleted, including all of its reports.

       If the measurement job is requested to be deleted after the
       stop time is reached: the OAM PM process resources are
       released, and then the measurement job is deleted, including
       all of its reports.";
    reference
      "ITU-T G.8051 v6.2 (01/2024): clause 10.2";
    action get-intermediate-report {
      description
        "This operation requests the intermediate PM data report of
         the on-going single-ended measurement interval.

         Intermediate means before the scheduled end of the
         measurement interval.

         If the request is received during the gap between two
         measurement intervals or at the end of a measurement
         interval, the report of the latest measurement interval is
         reported (with the same timestamp).

         If the request is received before the start-time, an error
         is reported.";
      output {
        container intermediate-report {
          presence
            "This container is present when the report is available
             (i.e., after the measurement job start-time)";
          description
            "Returns the requested intermediate PM data report of the
             on-demand single-ended measuement job, if available.";
          uses single-ended-pm-intermediate-report;
        }
      }
    }
    leaf oam-type {
      type single-ended-oam-type;
      must "not(derived-from-or-self(current(),
            'eth-oam:oam-lm-lmm')) or count(/dot1q-cfm:cfm/
            dot1q-cfm:maintenance-domain[dot1q-cfm:md-id=current()/
            ../../../../../dot1q-cfm:md-id]/
            dot1q-cfm:maintenance-association[dot1q-cfm:ma-id=
            current()/../../../../../dot1q-cfm:ma-id]/
            dot1q-cfm:maintenance-association-mep)=2" {
        error-message "The single-ended LMM/LMR OAM protocol "
                    + "(i.e.,' eth-oam:oam-lm-lmm') can only be "
                    + "used for measurement jobs within "
                    + "point-to-point Maintenance Entity Groups "
                    + "(MEGs) (i.e., when the /dot1q-cfm:cfm/"
                    + "dot1q-cfm:maintenance-domain/"
                    + "dot1q-cfm:maintenance-association/"
                    + "dot1q-cfm:maintenance-association-mep "
                    + "list has only 2 elements).";
        description
          "The single-ended LMM/LMR OAM protocol can only be used
           for measurement jobs within point-to-point Maintenance
           Entity Groups (MEGs).";
        reference
          "ITU-T G.8013 v6.1 (01/2024): clause 8.2.2";
      }
      must "derived-from-or-self(current(),'eth-oam:oam-dm') or
            (../eth-oam:oam-pdu-generation-type='single-series') or
            (../eth-oam:oam-pdu-generation-type='repetitive-series')
           " {
        error-message "The single instance "
                    + "(i.e., 'single-instance') and repetitive "
                    + "instance (i.e., 'repetitive-instance') OAM "
                    + "PDU generation types "
                    + "(i.e., 'eth-oam:oam-pdu-generation-type') "
                    + "are applicable only to single-ended "
                    + "DMM/DMR OAM protocol type "
                    + "(i.e., 'eth-oam:oam-dm').";
        description
          "The single instance and repetitive instance OAM PDU
           generation types are applicable only to single-ended
           DMM/DMR OAM protocol type.";
      }
      mandatory true;
      description
        "The type of the single-ended on-demand OAM protocol.";
    }
    uses on-demand-measurement-job-control;
    leaf destination-address {
      type ieee:mac-address;
      mandatory true;
      description
        "The Unicast MAC address of the target MEP.";
    }
    container dm {
      when "derived-from-or-self(../eth-oam:oam-type,
            'eth-oam:oam-dm')" {
        description
          "When the OAM protocol is single-ended DMM/DMR.";
      }
      description
        "Single-ended DMM/DMR OAM protocol configuration.";
      uses oam-dm-config;
    }
    container lm {
      when "derived-from-or-self(../eth-oam:oam-type,
            'eth-oam:oam-lm-lmm')" {
        description
          "When the OAM protocol is single-ended LMM/LMR.";
      }
      description
        "Single-ended LMM/LMR OAM protocol configuration.";
      uses oam-lm-config;
    }
    container sl {
      when "derived-from-or-self(../eth-oam:oam-type,
            'eth-oam:oam-sl')" {
        description
          "When the OAM protocol is single-ended SLM/SLR.";
      }
      description
        "Single-ended SLM/SLR OAM protocol configuration.";
      uses oam-sl-config;
    }
    container test {
      when "derived-from-or-self(../eth-oam:oam-type,
            'eth-oam:oam-tst-lbm')" {
        description
          "When the OAM protocol is single-ended LBM/LBR.";
      }
      description
        "Single-ended LBM/LBR OAM protocol configuration.

         Only one ITU-T OAM Loopback (Discovery, Series or Test)
         operation can be active on the MEP.

         The request to create an on-demand measurement job for
         single-ended LBM/LBR OAM protocol will be rejected if
         another on-demand measurement job for single-ended LBM/LBR
         OAM protocol exists on the same MEP or there is already an
         on-going ITU-T OAM Loopback operation (Discovery or Series)
         on the same MEP.";
      uses oam-test-config;
    }
    list report {
      key "time-stamp";
      config false;
      description
        "The list of reports, one for each measurement interval,
         of the on-demand PM measurement job.

         A report is created at the end of a measurement interval
         when the results are ready to be reported.

         When the start time is reached, the list of the existing
         reports, if any, is emptied out.";
      uses single-ended-pm-report;
    }
  }

  grouping on-demand-measurement-job-control {
    description
      "The common attributes of on-demand measurement job control.

       If the start time is not reached yet, it is possible to
       reconfigure the start time, the stop time, or both to anytime
       in the future with respect to the current time.

       After the start time is reached; if the stop time is not
       reached yet, it is possible to reconfigure only the stop time
       to anytime in the future with respect to the current time.

       If the stop time is reached, it is only possible to
       reconfigure the start time and stop time together to anytime
       in the future with respect to the current time.";
    reference
      "ITU-T G.8051 v6.2 (01/2024): clause 10.2";
    leaf start-time {
      type yang:date-and-time;
      description
        "The nominal start time of the on-demand measurement job.

         By default, it is set to the time the on-demand measurement
         job is created.";
    }
    leaf stop-time {
      when "(../eth-oam:oam-pdu-generation-type =
            'repetitive-instance') or
            (../eth-oam:oam-pdu-generation-type =
            'repetitive-series')" {
        description
          "When the OAM PDU generation type is a repetitive type.

           By default, it is set to never stop.";
      }
      type yang:date-and-time;
      description
        "The nominal stop time of the on-demand measurement job.";
    }
    leaf oam-pdu-generation-type {
      type oam-pdu-generation-type;
      mandatory true;
      description
        "The pattern that is used for the generation of OAM
         messages.";
    }
    leaf measurement-interval {
      when "(../eth-oam:oam-pdu-generation-type =
            'single-series') or (../eth-oam:oam-pdu-generation-type
            = 'repetitive-series')" {
        description
          "When the OAM PDU generation type is either a single
           series or a repetitive series.";
      }
      type uint16 {
        range "30..max";
      }
      units "seconds";
      mandatory true;
      description
        "The measurement interval.";
    }
    leaf repetition-period {
      when "(../eth-oam:oam-pdu-generation-type =
            'repetitive-instance') or
            (../eth-oam:oam-pdu-generation-type =
            'repetitive-series')" {
        description
          "When the OAM PDU generation type is either a repetitive
           instance or a repetitive series.";
      }
      type uint32 {
        range "6..max";
      }
      units "seconds";
      must "not (../eth-oam:oam-pdu-generation-type =
            'repetitive-series') or
            (. > ../eth-oam:measurement-interval)" {
        error-message "In a repetitive series (i.e., when "
                    + "'eth-oam:oam-pdu-generation-type="
                    + "repetitive-series'), the repetition "
                    + "period shall be greater than the "
                    + "measurement interval "
                    + "(i.e., 'eth-oam:measurement-interval').";
        description
          "In a repetitive series, the repetition period shall be
           greater than the measurement interval.";
      }
      mandatory true;
      description
        "The repetition period.";
    }
  }

  grouping dm-threshold-values {
    description
      "The threshold values used for frame delay measurement.";
    leaf granularity-period {
      type granularity-period;
      description
        "The granularity period of the current registers to which the
         thresholds apply.";
    }
    container near-end-overflow-threshold {
      description
        "The overflow threshold values used to generate an out of
         range (OOR) report for near-end delay measurement.";
      reference
        "ITU-T G.7710 v5.1 (11/2022): clause 10.1.7.2";
      uses dm-performance-data;
    }
    container far-end-overflow-threshold {
      description
        "The overflow threshold values used to generate an out of
         range (OOR) report for far-end delay measurement.";
      reference
        "ITU-T G.7710 v5.1 (11/2022): clause 10.1.7.2";
      uses dm-performance-data;
    }
    container bidirectional-overflow-threshold {
      description
        "The overflow threshold values used to generate an out of
         range (OOR) report for bidirectional delay measurement.";
      reference
        "ITU-T G.7710 v5.1 (11/2022): clause 10.1.7.2";
      uses dm-performance-data;
    }
  }

  grouping loopback-series-input {
    description
      "Additional input parameters to configure an OAM Loopback
       Series operation.";
    reference
      "ITU-T G.8021 v8.1 (01/2024): clause 8.1.8.2";
    leaf period {
      type uint32;
      units "milliseconds";
      description
        "The periodicity of the LBM OAM messages.

         The default value, the value range and the granularity
         of the values within the value range are implementation
         specific.";
    }
    leaf data-tlv-length {
      type uint16;
      units "octets";
      description
        "The Length of the Data TLV to be inserted within the
         LBM OAM messages.";
    }
  }

  grouping linktrace-input {
    description
      "Additional input parameters to configure an OAM Linktrace
       operation.";
    reference
      "ITU-T G.8021 v8.1 (01/2024): clause 8.1.13.2";
    leaf priority {
      type dot1q-types:priority-type;
      description
        "The priority value of the Linktrace operation.

         The default value is the same as the CCM priority.";
    }
  }

  grouping linktrace-reply {
    description
      "The information received from an OAM Linktrace Reply (LTR)
       message of an OAM Linktrace operation.";
    reference
      "ITU-T G.8021 v8.1 (01/2024): clause 8.1.13.2";
    uses linktrace-response;
    leaf ltr-source-address {
      type ieee:mac-address;
      mandatory true;
      description
        "The MAC Source Address (SA) of the returned Linktrace
         Reply (LTR) OAM message.";
    }
  }

  grouping linktrace-response {
    description
      "This grouping contains the Linktrace (LT) attributes which are
       in common with those defined in IEEE CFM YANG model.

       The data nodes names and types have been selected to enable
       replacing this grouping with a new grouping to be defined in
       a future version of IEEE CFM YANG model.

       This grouping shall not be re-used outside of this module.";
    reference
      "ITU-T G.8021 v8.1 (01/2024): clause 8.1.13.2";
    leaf ltr-ttl {
      type uint8 {
        range "0..255";
      }
      mandatory true;
      description
        "The value of the TTL field in the received LTR OAM
         Message.";
    }
    leaf ltr-forwarded {
      type boolean;
      description
        "Indicates whether the modified LTM OAM Message has been
         relayed or not based on the FwdYes flag of received LTR OAM
         Message.

         Implementations compliant with the 2006 edition of ITU-T
         G.8013 are not required to support the FwdYes flag of
         received LTR OAM Message. These implementations shall not
         report this attribute.";
      reference
        "ITU-T G.8013 v6.1 (01/2024): clause 9.6.2 and annex B";
    }
    leaf ltr-terminal-mep {
      type boolean;
      description
        "Indicates whether the Reply Egress TLV (or Reply Ingress
         TLV, if the Reply Egress TLV is not present) is a MEP or
         not.

         Implementations compliant with the 2006 edition of ITU-T
         G.8013 are not required to support the Reply Egress TLV nor
         the Reply Ingress TLV of received LTR OAM Message. These
         implementations shall not report this attribute.";
      reference
        "ITU-T G.8013 v6.1 (01/2024): clause 9.6.2 and annex B";
    }
    container ltr-last-egress-identifier {
      presence
        "When present indicates that the LTR Egress Identifier TLV
         was present in the received LTR OAM Message.";
      description
        "The information in the Last Egress Identifier field of LTR
         Egress Identifier TLV in the received LTR OAM Message.";
      reference
        "ITU-T G.8013 v6.1 (01/2024): clause 9.6.2 and annex B";
      uses dot1q-cfm:ltm-egress-identifier-grouping;
    }
    container ltr-next-egress-identifier {
      presence
        "When present indicates that the LTR Egress Identifier TLV
         was present in the received LTR OAM Message.";
      description
        "The information in the Next Egress Identifier field of LTR
         Egress Identifier TLV in the received LTR OAM Message.";
      reference
        "ITU-T G.8013 v6.1 (01/2024): clause 9.6.2 and annex B";
      uses dot1q-cfm:ltm-egress-identifier-grouping;
    }
    leaf ltr-relay {
      type cfm-types:relay-action-field-value-type;
      description
        "The value of the Relay Action field in the received LTR OAM
         Message.";
      reference
        "ITU-T G.8013 v6.1 (01/2024): clause 9.6.2";
    }
    leaf ltr-ingress {
      type cfm-types:ingress-action-field-value-type;
      description
        "The value of the Ingress Action field of the Reply Ingress
         TLV in the received LTR OAM Message.

         This leaf is not present if the Reply Ingress TLV was not
         present in the received LTR OAM Message.";
      reference
        "ITU-T G.8013 v6.1 (01/2024): clause 9.6.2";
    }
    leaf ltr-ingress-mac {
      when '../eth-oam:ltr-ingress';
      type ieee:mac-address;
      mandatory true;
      description
        "The MAC address in the Ingress MAC Address field of the
         Reply Ingress TLV in the received LTR OAM Message.";
      reference
        "ITU-T G.8013 v6.1 (01/2024): clause 9.6.2";
    }
    leaf ltr-egress {
      type cfm-types:egress-action-field-value-type;
      description
        "The value of the Egress Action field of the Reply Egress TLV
         in the received LTR OAM Message.

         This leaf is not present if the Reply Egress TLV was not
         present in the received LTR OAM Message.";
      reference
        "ITU-T G.8013 v6.1 (01/2024): clause 9.6.2";
    }
    leaf ltr-egress-mac {
      when '../eth-oam:ltr-egress';
      type ieee:mac-address;
      mandatory true;
      description
        "The MAC address in the Egress MAC Address field of the Reply
         Egress TLV in the received LTR OAM Message.";
      reference
        "ITU-T G.8013 v6.1 (01/2024): clause 9.6.2";
    }
  }

  /*
   * Data Nodes
   */

  augment "/dot1q-cfm:cfm" {
    description
      "Augment CFM top-level container";
    container threshold-profiles {
      description
        "The top-level container for the list of Performance
         Monitoring (PM) threshold profiles.";
      list threshold-profile {
        key "threshold-profile-id";
        description
          "The list of Performance Monitoring (PM) threshold
           profiles.

           Multiple profiles may be created, e.g., to support
           different grade of services.";
        reference
          "ITU-T G.7710 v5.1 (11/2022): clause 8.11";
        leaf threshold-profile-id {
          type string;
          description
            "The identifier of the threshold profile.";
        }
        list dm-threshold {
          key "granularity-period";
          description
            "The list of threshold settings for the delay
             measurement data for different granularity periods
             (e.g., 15min, 24h).";
          uses dm-threshold-values;
        }
      }
    }
  }

  augment "/dot1q-cfm:cfm/dot1q-cfm:maintenance-domain"
        + "/dot1q-cfm:maintenance-association/dot1q-cfm:ma-name" {
    description
      "Augment MA name.";
    case ma-name-itu {
      description
        "ITU-T MEG ID format.";
      container ma-name-itu {
        description
          "Attributes for the ITU-T MEG ID format.";
        uses ma-name-itu;
      }
    }
  }

  augment "/dot1q-cfm:cfm/dot1q-cfm:maintenance-group" {
    description
      "Augment the Maintenance Group.";
    list mip {
      when "/dot1q-cfm:cfm/dot1q-cfm:maintenance-domain
            [dot1q-cfm:md-id=current()/../dot1q-cfm:md-id]
            /dot1q-cfm:maintenance-association
            [dot1q-cfm:ma-id=current()/../dot1q-cfm:ma-id]
            /dot1q-cfm:mhf-creation='mhf-none'
            or
            (/dot1q-cfm:cfm/dot1q-cfm:maintenance-domain
            [dot1q-cfm:md-id=current()/../dot1q-cfm:md-id]
            /dot1q-cfm:mhf-creation='mhf-none'
            and
            /dot1q-cfm:cfm/dot1q-cfm:maintenance-domain
            [dot1q-cfm:md-id=current()/../dot1q-cfm:md-id]
            /dot1q-cfm:maintenance-association
            [dot1q-cfm:ma-id=current()/../dot1q-cfm:ma-id]/
            dot1q-cfm:mhf-creation='mhf-defer'
            )" {
        description
          "When indirect MIP creation is disabled.";
        reference
          "IEEE Std 802.1Q-2018: clause 22.2.3";
      }
      key "name";
      description
        "The list of MIPs.";
      reference
        "ITU-T G.8013 v6.1 (01/2024): clauses 3.2.9 and 6";
      leaf name {
        type string;
        description
          "An identifier of the MIP.";
      }
      leaf mip-mac {
        type ieee:mac-address;
        config false;
        mandatory true;
        description
          "This attribute contains the MAC address
           of the MIP instance.";
      }
      leaf is-full-mip {
        type boolean;
        default "true";
        config false;
        description
          "This attribute indicates whether the MIP is a full MIP
           (true) or a down-half MIP (false).";
      }
    }
  }

  augment "/dot1q-cfm:cfm/dot1q-cfm:maintenance-group"
        + "/dot1q-cfm:mep" {
    when '../dot1q-cfm:maintenance-group-id';
    description
      "Augment the MEP."; // container linktrace-state
    action get-saved-ccm {
      description
        "This operation is used to request the saved latest CCM OAM
         message that caused a defect to be raised.";
      reference
        "ITU-T G.8021 v8.1 (01/2024): clause 8.1.7.3";
      output {
        container saved-ccm {
          presence
            "This container is present when the saved latest CCM
             OAM message that caused a defect to be raised is
             available.";
          description
            "The saved latest CCM OAM message, together with the
             priority value and Drop Eligibility (DE) information,
             that caused a defect to be raised.";
          leaf priority {
            type dot1q-types:priority-type;
            description
              "The priority value of the saved CCM OAM message.";
          }
          leaf drop-eligible {
            type boolean;
            description
              "The Drop Eligibility (DE) of the saved CCM OAM
               message.

               A value 'true' means that the OAM message is Drop
               Eligible while a value 'false' means that the OAM
               message is not Drop Eligible.";
          }
          leaf ccm-oam-message {
            type yang:hex-string;
            description
              "The hexdump of the saved CCM OAM message.";
          }
        }
      }
    }
    leaf tcm-mep {
      type boolean;
      description
        "Indicates whether the MEP is a TCM or an NCM MEP.

         When not present, it is not specified whether
         the MEP is a TCM or an NCM MEP.";
      reference
        "ITU-T G.8052 v3.0 (12/2018): clause 5.2.1";
    }
    leaf client-mel {
      when "../eth-oam:tcm-mep='true'" {
        description
          "When the MEP is a TCM MEP.";
      }
      type cfm-types:md-level-type;
      must ". > /dot1q-cfm:cfm/dot1q-cfm:maintenance-domain
            [dot1q-cfm:md-id=current()/../../dot1q-cfm:md-id]
            /dot1q-cfm:md-level" {
        error-message "The Maintenance Domain (MD) level "
                    + "(MEG level) at which the most immediate "
                    + "client sub-layer MIPs and MEPs exist shall "
                    + "be greater than the MEG level of the MD "
                    + "(i.e., the '/dot1q-cfm:cfm/"
                    + "dot1q-cfm:maintenance-domain/"
                    + "dot1q-cfm:md-level' of the "
                    + "'dot1q-cfm:md-id' MD).";
        description
          "The Maintenance Domain (MD) level (MEG level) at which
           the most immediate client sub-layer MIPs and MEPs exist
           shall be greater than the MEG level of the MD.";
      }
      mandatory true;
      description
        "The Maintenance Domain level (MEG level) at which the most
         immediate client sub-layer MIPs and MEPs exist.";
      reference
        "ITU-T G.8013 v6.1 (01/2024): clause 6.2";
    }
    container eth-ais {
      when "../eth-oam:tcm-mep='true'" {
        description
          "When the MEP is a TCM MEP.";
      }
      description
        "Configuration of AIS generation.";
      reference
        "ITU-T G.8021 v8.1 (01/2024): clause 8.1.4";
      uses eth-ais-lck-common;
    }
    container eth-lck {
      when "../eth-oam:tcm-mep='true'" {
        description
          "When the MEP is a TCM MEP.";
      }
      description
        "Configuration of LCK generation.";
      reference
        "ITU-T G.8021 v8.1 (01/2024): clause 8.1.2";
      uses eth-ais-lck-common;
    }
    container eth-csf {
      when "count(/dot1q-cfm:cfm/
            dot1q-cfm:maintenance-domain[dot1q-cfm:md-id=current()/
            ../../dot1q-cfm:md-id]/
            dot1q-cfm:maintenance-association[dot1q-cfm:ma-id=
            current()/../../dot1q-cfm:ma-id]/
            dot1q-cfm:maintenance-association-mep)=2" {
        description
          "When the Maintenance Entity Group (MEG) is
           point-to-point.";
        reference
          "ITU-T G.8013 v6.1 (01/2024): clause 7.12";
      }
      description
        "Configuration of CSF generation and reception.";
      reference
        "ITU-T G.8021 v8.1 (01/2024): clauses 8.1.16 and 8.1.17";
      leaf csf-config {
        type csf-config;
        default "disabled";
        description
          "The configuration of the CSF generation process,
           describing whether the CSF generation process is enabled
           or disabled and, in case the process is enabled, whether
           the client defect clear indication (C-DCI) is also enabled
           or disabled and whether the reporting of the client
           reverse defect indication (C-RDI) and the forward defect
           indication (C-FDI) conditions is also enabled or
           disabled.";
      }
      leaf csf-period {
        type csf-period;
        default "1sec";
        description
          "The CSF PDU generation period.";
        reference
          "ITU-T G.8013 v6.1 (01/2024): Table 9-6";
      }
      leaf csf-priority {
        type dot1q-types:priority-type;
        description
          "The priority value of the generated CSF messages.

           The default value is the same as the CCM priority.";
      }
      leaf is-csf-reported {
        type boolean;
        default "true";
        description
          "Configures whether the CSF secondary failure should be
           reported or not.";
      }
    } // container eth-csf
    container eth-bandwidth-notifications {
      description
        "The top-level container for the list of the bandwidth
         notification reports received by the MEP.";
      list eth-bandwidth-notification {
        config false;
        description
          "The list of the bandwidth notification reports received
           by the MEP.";
        reference
          "ITU-T G.8021 v8.1 (01/2024): clause 8.1.19";
        leaf source-mac-address {
          type ieee:mac-address;
          config false;
          mandatory true;
          description
            "The MAC Address of the sever layer MEP which has
             generated the bandwidth notification message.";
        }
        leaf port-id {
          type uint32 {
            range "1..max";
          }
          config false;
          mandatory true;
          description
            "The identifier for the port which is associated with the
             bandwidth report.

             It is unique within the MEG.";
        }
        leaf nominal-bandwidth {
          type uint32;
          units "Megabits per second";
          config false;
          mandatory true;
          description
            "The reported nominal bandwidth of the link.";
        }
        leaf current-bandwidth {
          type uint32;
          units "Megabits per second";
          config false;
          mandatory true;
          description
            "The reported current bandwidth of the link.";
        }
      }
    } // container eth-bandwidth-notifications
    container deg-detection {
      description
        "The configuration of parameters used for detecting the
         'degraded signal' (DEG) defect.

         It is applicable only when LM CCM is enabled.";
      reference
        "ITU-T G.8021 v8.1 (01/2024): clause 6.1.3.4

         ITU-T G.806 v5.4 (11/2022): clause 6.2.3.1.3 and
         Table 7.1";
      leaf lm-deg-m {
        type uint8 {
          range "2..10";
        }
        units "seconds";
        description
          "The number of consecutive bad seconds necessary for
           declaring a 'degraded' condition.

           The default value is 7 seconds.

           Equipment designed prior to the 2016 version of G.806 may
           use the default of 10.";
      }
      leaf lm-deg-thr {
        type decimal64 {
          fraction-digits 16;
          range "0..100";
        }
        units "%";
        description
          "The threshold value for declaring a 'bad second'.

           If not configured, a default value shall be assigned by
           the system.

           Equipment designed prior to the 2016 version of G.806 may
           use a default value of 30%.";
      }
      leaf lm-tf-min {
        type uint32;
        description
          "The necessary number of transmitted frames to enable the
           detection of 'bad seconds'.";
      }
      leaf lm-m {
        type uint8 {
          range "2..10";
        }
        units "seconds";
        description
          "The number of consecutive good seconds necessary for the
           clearing of a 'degraded' condition.

           The default value is 7 seconds.

           Equipment designed prior to the 2016 version of G.806 may
           use the default of 10.";
      }
    } // container deg-detection
    leaf eth-aps-priority {
      when "../eth-oam:tcm-mep='true'" {
        description
          "When the MEP is a TCM MEP.";
      }
      type dot1q-types:priority-type;
      description
        "This attribute specifies the priority of the APS messages,
         when generated by the MEP.

         The default value is the same as the CCM priority.";
      reference
        "ITU-T G.8021 v8.1 (01/2024): clause 8.1.5";
    }
    list measurement-job {
      key "measurement-job-id";
      description
        "The list of Measurement Jobs that are being performed by the
         MEP.";
      uses eth-mea-job-pac;
    }
    container loopback-discovery-state {
      presence
        "When present, it indicates that an ITU-T OAM Loopback
         Discovery operation has been requested (it can be on-going
         or ended).

         It is created or, if it already exists, overwritten when an
         OAM Loopback Discovery operation is requested.";
      config false;
      description
        "The state of the latest OAM Loopback Discovery operation.";
      reference
        "ITU-T G.8021 v8.1 (01/2024): clause 8.1.8.2";
      container input {
        description
          "The input parameters used to request the latest OAM
           Loopback Discovery operation.";
        uses dot1q-cfm:loopback-input-grouping {
          refine "lbm-destination" {
            mandatory false;
          }
        }
      }
      container result {
        presence
          "The result is created at the end of OAM Loopback Discovery
           operation when ready to be reported.

           When an OAM Loopback Discovery operation is requested, the
           existing result, if any, is emptied out.";
        description
          "The result of the latest OAM Loopback Discovery
           operation.";
        leaf-list peer-mep-address {
          type ieee:mac-address;
          description
            "The list of discovered MAC addresses of the peer MEPs.";
        }
      }
    } // container loopback-discovery-state
    container loopback-series-state {
      presence
        "When present, it indicates that an ITU-T OAM Loopback
         Series operation has been requested (it can be on-going
         or ended).

         It is created or, if it already exists, overwritten when an
         OAM Loopback Series operation is requested.";
      config false;
      description
        "The state of the latest OAM Loopback Series operation.";
      reference
        "ITU-T G.8021 v8.1 (01/2024): clause 8.1.8.2";
      container input {
        description
          "The input parameters used to request the latest OAM
           Loopback Series operation.";
        uses dot1q-cfm:loopback-input-grouping {
          refine "lbm-destination" {
            mandatory false;
          }
        }
        uses loopback-series-input;
      }
      container result {
        presence
          "The result is created at the end of OAM Loopback Series
           operation when ready to be reported.

           When an OAM Loopback Series operation is requested, the
           existing result, if any, is emptied out.";
        description
          "The result of the latest OAM Loopback Series operation.";
        leaf received {
          type uint16 {
            range "0..1024";
          }
          description
            "Number of OAM Loopback Reply (LBR) Messages which
             have been received.";
        }
        leaf out-of-order {
          type uint16 {
            range "0..1024";
          }
          description
            "Number of the OAM Loopback Reply (LBR) Messages which
             have been received out of order.";
        }
      }
    } // container loopback-series-state
    container linktrace-state {
      presence
        "When present, it indicates that an ITU-T OAM Linktrace
         operation has been requested (it can be on-going or ended).

         It is created or, if it already exists, overwritten when an
         OAM Linktrace operation is requested.";
      config false;
      description
        "The state of the latest OAM Linktrace operation.";
      reference
        "ITU-T G.8021 v8.1 (01/2024): clause 8.1.13.2";
      container input {
        description
          "The input parameters used to request the latest OAM
           Linktrace operation.";
        uses dot1q-cfm:linktrace-input-grouping {
          refine "ltr-target" {
            mandatory false;
          }
        }
        uses linktrace-input;
      }
      container result {
        presence
          "The result is created at the end of OAM Linktrace
           operation when ready to be reported.

           When an OAM Linktrace operation is requested, the existing
           result, if any, is emptied out.";
        description
          "The result of the latest OAM Linktrace operation.";
        list reply {
          description
            "The list of received Linktrace replies (from received
             LTR OAM messages).";
          uses linktrace-reply;
        }
      }
    } // action get-saved-ccm
  } // Augment MEP

  augment "/dot1q-cfm:cfm/dot1q-cfm:maintenance-group"
        + "/dot1q-cfm:mep/dot1q-cfm:transmit-loopback"
        + "/dot1q-cfm:input" {
    description
      "Augment the input of the Transmit Loopback action.";
    choice loopback-operation {
      description
        "The type of ITU-T OAM Loopback (Discovery or Series)
         operation being requested.

         If not specified, the requested Loopback operation is not an
         ITU-T Loopback operation.

         Only one ITU-T OAM Loopback (Discovery, Series or Test)
         operation can be active on the MEP.

         The request to perform an ITU-T OAM Loopback operation will
         be rejected if there is already an on-going ITU-T OAM
         Loopback operation (Discovery, Series or Test).

         Note: The ITU-T OAM Loopback Test operations are modelled
         as a single-ended measurement job. Therefore an ITU-T OAM
         Loopback (Discovery or Series) operation will be rejected
         when an on-demand measurement job for single-ended LBM/LBR
         OAM protocol exists on the same MEP.";
      reference
        "ITU-T G.8021 v8.1 (01/2024): clause 8.1.8";
      container loopback-discovery {
        must 'not (../dot1q-cfm:lbm-messages)' {
          description
            "When an ITU-T OAM Loopback Discovery operation is
             requested, the number of LBM messages shall not be
             configured: only the default value 1 shall be used.";
        }
        must 'not (../dot1q-cfm:lbm-drop-eligible)' {
          description
            "When an ITU-T OAM Loopback Discovery operation is
             requested, the LBM Drop Eligibility shall not be
             configured: only the default value False shall be
             used.";
        }
        must 'not (../dot1q-cfm:lbm-data-tlv)' {
          description
            "When an ITU-T OAM Loopback Discovery operation is
             requested, the LBM Data TLV shall not be configured:
             no Data TLV shall be inserted in the OAM LBM Message.";
        }
        presence
          "When present, it indicates a request for an ITU-T OAM
           Loopback Discovery operation.";
        description
          "The configuration of an ITU-T OAM Loopback Discovery
           operation.

           When an ITU-T OAM Loopback Discovery operation is
           requested:
           - the Target MAC address shall be set to multicast class 1
             MAC address corresponding to the Maintenance Domain (MD)
             level (MEG level) of the MEP;
           - the LBM Priority shall be set to the same value of the
             CCM priority.";
      }
      container loopback-series {
        must 'not (../dot1q-cfm:lbm-dest-mcast-class1-mac-address)' {
          description
            "When an ITU-T OAM Loopback Series operation is
             requested, the Target MAC address shall be an unicast
             MAC address.";
        }
        must 'not (../dot1q-cfm:lbm-data-tlv)' {
          description
            "When an ITU-T OAM Loopback Series operation is
             requested, the LBM Data TLV shall not be configured: the
             LBM Data TLV shall not be configured: the Data TLV
             Length (eth-oam:data-tlv-length) shall be used
             instead.";
        }
        presence
          "When present, it indicates a request for an ITU-T OAM
           Loopback Series operation.";
        description
          "The configuration of an ITU-T OAM Loopback Series
           operation.";
        uses loopback-series-input;
      }
    }
  } // Augment Transmit LB input

  augment "/dot1q-cfm:cfm/dot1q-cfm:maintenance-group"
        + "/dot1q-cfm:mep/dot1q-cfm:transmit-linktrace"
        + "/dot1q-cfm:input" {
    description
      "Augment the input for Transmit Linktrace action.";
    uses linktrace-input;
  } // Augment Transmit LT input

}
